EMAP-MIB DEFINITIONS ::= BEGIN
                                             IMPORTS
                                             huaweiUtility
                                                 FROM HUAWEI-MIB
                                             OBJECT-GROUP, NOTIFICATION-GROUP
                                                 FROM SNMPv2-CONF
                                             Integer32, Unsigned32, OBJECT-TYPE, MODULE-IDENTITY, NOTIFICATION-TYPE
                                                 FROM SNMPv2-SMI
                                             TEXTUAL-CONVENTION
                                                 FROM SNMPv2-TC;
hwSiteMonitorMIB MODULE-IDENTITY
LAST-UPDATED "201210240000Z"
ORGANIZATION 
                                             "Huawei Technologies Co.,Ltd."
CONTACT-INFO 
                                             "Floor 5, Block 4, R&D Building,
                                             Huawei Longgang Production Base,
                                             Shenzhen,   P.R.C.
                                             http://www.huawei.com
                                             Zip: 518129."
DESCRIPTION 
                                             "EMAP MIB defines MIB objects which provides load and backup management, patch management NMS interfaces.
                                             The current version is v1.01"
REVISION "201210240000Z"
                                             DESCRIPTION 
                                             "Huawei emap mib v1.00"
::= { huaweiUtility 164 }

DisplayString ::= TEXTUAL-CONVENTION
                                             STATUS current
                                             DESCRIPTION 
                                             "Description."
                                             SYNTAX OCTET STRING (SIZE (1..64))
                                             
                                             RowStatus ::= TEXTUAL-CONVENTION
                                             STATUS current
                                             DESCRIPTION 
                                             "Description."
                                             SYNTAX INTEGER
                                             {
                                                     active(1),
                                                     notInService(2),
                                                     notReady(3),
                                                     createAndGo(4),
                                                     createAndWait(5),
                                                     destroy(6)
                                             }
                                             
                                             DateAndTime ::= TEXTUAL-CONVENTION
                                             STATUS current
                                             DESCRIPTION 
                                             "Description."
                                             SYNTAX OCTET STRING (SIZE (8..11))
                                             
                                             RunStatus ::= TEXTUAL-CONVENTION
                                             STATUS current
                                             DESCRIPTION 
                                                     "This integer value represents running status of the system. 
                                                     Depending on situation there may be limits on allowed values.
                                                     Operational values:
                                                     (1) unknown - status has not yet been defined
                                                     (2) normal - there are no activated alarms
                                                     (3) alarm - alarm status
                                             "
                                             SYNTAX INTEGER
                                             {
                                                     unknow(1),
                                                     normal(2),
                                                     alarm(3)
                                             }
                                             
                                             MeasuresRange ::= TEXTUAL-CONVENTION
                                             STATUS current
                                             DESCRIPTION 
                                             "Description."
                                             SYNTAX Integer32
                                             
                                             TruthValue ::= TEXTUAL-CONVENTION
                                             STATUS current
                                             DESCRIPTION 
                                             "Description."
                                             SYNTAX INTEGER
                                             {
                                                     true(1),
                                                     flase(2)
                                             }
hwSiteMonitorMIBObjects OBJECT IDENTIFIER ::= { hwSiteMonitorMIB 1 }

hwSiteInfo OBJECT IDENTIFIER ::= { hwSiteMonitorMIBObjects 1 }

hwSiteSummary OBJECT IDENTIFIER ::= { hwSiteInfo 1 }

hwSiteId OBJECT-TYPE
SYNTAX Unsigned32
MAX-ACCESS read-only
STATUS current
DESCRIPTION
"Site ID, default value: 000,000.
  Naming rule of the site device ID (six digits): The first three digits indicate the device name and the last three digits indicate the serial number (SN) of the device. If the last three digits are 000, it indicates a virtual device."
 ::= { hwSiteSummary 1 }

hwSiteName OBJECT-TYPE
SYNTAX OCTET STRING (SIZE (0..63))
MAX-ACCESS read-write
STATUS current
DESCRIPTION
"Site name, which users can configure, is used to specify a site.  Otherwise, the configured character can not be any other languages except English."
 ::= { hwSiteSummary 2 }

hwSiteAdminAddr OBJECT-TYPE
SYNTAX Unsigned32 (0..65535)
MAX-ACCESS read-write
STATUS current
DESCRIPTION
"Site administrant address, which users can assigned, is the unique ID of a site. It is used for device management by NMS, and value range is 0 to 65535. "
 ::= { hwSiteSummary 3 }

hwSiteDescription OBJECT-TYPE
SYNTAX OCTET STRING (SIZE (0..63))
MAX-ACCESS read-write
STATUS current
DESCRIPTION
"Site description. It is of the character string type. It is used to describe the site information such as the site location, which users can configure.  Otherwise, the configured character can not be any other languages except English."
 ::= { hwSiteSummary 4 }

hwNetIdentifier OBJECT-TYPE
SYNTAX OCTET STRING (SIZE (0..63))
MAX-ACCESS read-write
STATUS current
DESCRIPTION
"NE ID. It is of the character string type. It is the unique ID of the site (an independent network element (NE)) on the network. Otherwise, the configured character can not be any other languages except English."
 ::= { hwSiteSummary 5 }

hwSiteIp OBJECT-TYPE
SYNTAX OCTET STRING (SIZE (8..16))
MAX-ACCESS read-only
STATUS current
DESCRIPTION
"Site IP address, default value is 192.168.0.10. Users need to configure the site IP address."
 ::= { hwSiteSummary 6 }

hwSiteNetmask OBJECT-TYPE
SYNTAX OCTET STRING (SIZE (8..16))
MAX-ACCESS read-only
STATUS current
DESCRIPTION
"Site netmask, default value is 255.255.255.0. Users need to configure the site netmask."
 ::= { hwSiteSummary 7 }

hwSiteGateway OBJECT-TYPE
SYNTAX OCTET STRING (SIZE (8..16))
MAX-ACCESS read-only
STATUS current
DESCRIPTION
"Site gateway, default value: 192.168.0.1. Users need to configure the site gateway."
 ::= { hwSiteSummary 8 }

hwSiteDGWorkStatus OBJECT-TYPE
SYNTAX INTEGER
{
idle(1),
working(2),
unknown(255)
}
MAX-ACCESS read-only
STATUS current
DESCRIPTION
"State of the diesel working state. It is an enumeration type: 
  If the enumeration value is 1, it indicates that the diesel is in the idle state;
  If the enumeration value is 2, it indicates that the diesel is in the working state;     
  If the enumeration value is 255, it indicates diesel operation status unknown."
 ::= { hwSiteSummary 9 }

hwSiteRunningStatus OBJECT-TYPE
SYNTAX INTEGER
{
normal(1),
alarm(2)
}
MAX-ACCESS read-only
STATUS current
DESCRIPTION
"State of the site alarm state. It is an enumeration type: 
  If the enumeration value is 1, it indicates that the site is in the normal state;
  If the enumeration value is 2, it indicates that the site is in the alarm state."
 ::= { hwSiteSummary 10 }

hwSiteAlarms OBJECT IDENTIFIER ::= { hwSiteInfo 2 }

hwDeviceTrapOrdinalNumber OBJECT-TYPE
SYNTAX Unsigned32
MAX-ACCESS read-write
STATUS current
DESCRIPTION
"Site device event trap serial number (SN) is the unique ID of the device event trap. It is used to resend and synchronize event traps. Its value range is 0 to 4294967295. When the value exceeds the maximum value, the system automatically clears the value and numbers the alarm from 0 to 4294967295.   If the network management system (NMS) recieve the alarm number is not consequential, in such case that it notifies the SNMP agent the event trap number required.  So the monitor send the 100 event trap messages in maximum, after consequencial number required by NMS again. Specially, if NMS set the value to 0, the agent would clear the alarm queue automatically."
 ::= { hwSiteAlarms 1 }

hwAlarmTrapOrdinalNumber OBJECT-TYPE
SYNTAX Unsigned32
MAX-ACCESS read-write
STATUS current
DESCRIPTION
"Site alarm serial number (SN) is the unique ID of the alarm Trap. It is used to resend and synchronize alarms. Its value range is 0 to 4294967295. When the value exceeds the maximum value, the system automatically clears the value and numbers the alarm from 0 to 4294967295.  
  If the network management system (NMS) recieve the alarm number is not consequential, in such case that it notifies the SNMP agent the alarm number required.  So the monitor send the 100 alarm messages in maximum, after consequencial number required by NMS again. Specially, if NMS set the value to 0, the agent would clear the alarm queue automatically."
 ::= { hwSiteAlarms 2 }

hwAlarmQuantity OBJECT-TYPE
SYNTAX Unsigned32 (0..65535)
MAX-ACCESS read-only
STATUS current
DESCRIPTION
"Alarm number in site alarm list which are support. It is used for alarm list management by NMS, and value range is 0 to 65535. "
 ::= { hwSiteAlarms 3 }

hwSiteActiveAlarmTable OBJECT-TYPE
SYNTAX SEQUENCE OF HwSiteActiveAlarmEntry
MAX-ACCESS not-accessible
                                             STATUS current
                                             DESCRIPTION
""
 ::= { hwSiteAlarms 99 }

hwSiteActiveAlarmEntry OBJECT-TYPE
SYNTAX HwSiteActiveAlarmEntry
MAX-ACCESS not-accessible
                                             STATUS current
                                             DESCRIPTION
""
INDEX { hwActiveAlarmIndex }
 ::= { hwSiteActiveAlarmTable 1 }

HwSiteActiveAlarmEntry ::= SEQUENCE {
hwActiveAlarmIndex
 Integer32,
hwActiveAlarmText
 OCTET STRING,
hwActiveAlarmLevel
 INTEGER,
hwActiveAlarmSigDesc
 OCTET STRING,
hwActiveAlarmTime
 OCTET STRING,
hwActiveAlarmRowStatus
 RowStatus
}

hwActiveAlarmIndex OBJECT-TYPE
SYNTAX Integer32 (1..65535)
MAX-ACCESS read-only
STATUS current
DESCRIPTION
"Site active alarm table index. It is the unique ID of the site alarm."
 ::= { hwSiteActiveAlarmEntry 1 }

hwActiveAlarmText OBJECT-TYPE
SYNTAX OCTET STRING (SIZE (0..63))
MAX-ACCESS read-only
STATUS current
DESCRIPTION
"Active alarm name. It is of the character string type, and used to specify the content of a specific alarm.  "
 ::= { hwSiteActiveAlarmEntry 2 }

hwActiveAlarmLevel OBJECT-TYPE
SYNTAX INTEGER
{
critical(1),
major(2),
minor(3),
warning(4),
unknown(255)
}
MAX-ACCESS read-only
STATUS current
DESCRIPTION
"Active alarm level, which users can configure the alarm severity, is an enumeration type:
    If the enumeration value is 1, it indicates a critical alarm;
    If the enumeration value is 2, it indicates a major alarm;
    If the enumeration value is 3, it indicates a minor alarm;
    If the enumeration value is 4, it indicates a warning;"
 ::= { hwSiteActiveAlarmEntry 3 }

hwActiveAlarmSigDesc OBJECT-TYPE
SYNTAX OCTET STRING (SIZE (0..127))
MAX-ACCESS read-only
STATUS current
DESCRIPTION
"Active alarm signal description. It is used to add and describe alarm content. Users can define the description of the alarm.
  Otherwise, the configured character can not be any other languages except English."
 ::= { hwSiteActiveAlarmEntry 4 }

hwActiveAlarmTime OBJECT-TYPE
SYNTAX OCTET STRING (SIZE (0..63))
MAX-ACCESS read-only
STATUS current
DESCRIPTION
"Active alarm time. It is of the character string type, and used to specify the content of a specific alarm.  "
 ::= { hwSiteActiveAlarmEntry 5 }

hwActiveAlarmRowStatus OBJECT-TYPE
SYNTAX RowStatus
MAX-ACCESS read-create
STATUS current
DESCRIPTION
"Rowstatus of active alarm table."
 ::= { hwSiteActiveAlarmEntry 100 }

hwSiteAlarmTable OBJECT-TYPE
SYNTAX SEQUENCE OF HwSiteAlarmEntry
MAX-ACCESS not-accessible
                                             STATUS current
                                             DESCRIPTION
"/"
 ::= { hwSiteAlarms 100 }

hwSiteAlarmEntry OBJECT-TYPE
SYNTAX HwSiteAlarmEntry
MAX-ACCESS not-accessible
                                             STATUS current
                                             DESCRIPTION
"/"
INDEX { hwAlarmIndex }
 ::= { hwSiteAlarmTable 1 }

HwSiteAlarmEntry ::= SEQUENCE {
hwAlarmIndex
 Integer32,
hwAlarmText
 OCTET STRING,
hwAlarmLevel
 INTEGER,
hwAlarmSigDesc
 OCTET STRING,
hwAlarmRowStatus
 RowStatus
}

hwAlarmIndex OBJECT-TYPE
SYNTAX Integer32 (1..65535)
MAX-ACCESS read-only
STATUS current
DESCRIPTION
"Site alarm table index. It is the unique ID of the site alarm."
 ::= { hwSiteAlarmEntry 1 }

hwAlarmText OBJECT-TYPE
SYNTAX OCTET STRING (SIZE (0..63))
MAX-ACCESS read-only
STATUS current
DESCRIPTION
"Alarm name. It is of the character string type, and used to specify the content of a specific alarm.  "
 ::= { hwSiteAlarmEntry 2 }

hwAlarmLevel OBJECT-TYPE
SYNTAX INTEGER
{
critical(1),
major(2),
minor(3),
warning(4),
unknown(255)
}
MAX-ACCESS read-write
STATUS current
DESCRIPTION
"Alarm level, which users can configure the alarm severity, is an enumeration type:
  If the enumeration value is 1, it indicates a critical alarm;
  If the enumeration value is 2, it indicates a major alarm;
  If the enumeration value is 3, it indicates a minor alarm;
  If the enumeration value is 4, it indicates a warning; "
 ::= { hwSiteAlarmEntry 3 }

hwAlarmSigDesc OBJECT-TYPE
SYNTAX OCTET STRING (SIZE (0..127))
MAX-ACCESS read-only
STATUS current
DESCRIPTION
"Alarm signal description. It is used to add and describe alarm content. Users can define the description of the alarm. Otherwise, the configured character can not be any other languages except English."
 ::= { hwSiteAlarmEntry 4 }

hwAlarmRowStatus OBJECT-TYPE
SYNTAX RowStatus
MAX-ACCESS read-create
STATUS current
DESCRIPTION
"RowStatus of site alarms table."
 ::= { hwSiteAlarmEntry 100 }

hwSiteMonitors OBJECT IDENTIFIER ::= { hwSiteMonitorMIBObjects 2 }

hwMonitorsGroup OBJECT IDENTIFIER ::= { hwSiteMonitors 1 }

hwMonsGroupId OBJECT-TYPE
SYNTAX Unsigned32
MAX-ACCESS read-only
STATUS current
DESCRIPTION
"Site monitor group ID, is the unique ID of the site monitors."
 ::= { hwMonitorsGroup 1 }

hwMonsGroupName OBJECT-TYPE
SYNTAX OCTET STRING (SIZE (0..63))
MAX-ACCESS read-write
STATUS current
DESCRIPTION
"Site monitor group name is of the character string type, used to specify the monitor group. Users can configure it. Otherwise, the configured character can not be any other languages except English."
 ::= { hwMonitorsGroup 2 }

hwMonsQuantity OBJECT-TYPE
SYNTAX Unsigned32 (0..100)
MAX-ACCESS read-only
STATUS current
DESCRIPTION
"Total site intelligent monitors. Units:pcs."
 ::= { hwMonitorsGroup 3 }

hwMonitor OBJECT IDENTIFIER ::= { hwSiteMonitors 2 }

hwMonitorTable OBJECT-TYPE
SYNTAX SEQUENCE OF HwMonitorEntry
MAX-ACCESS not-accessible
                                             STATUS current
                                             DESCRIPTION
"/"
 ::= { hwMonitor 1 }

hwMonitorEntry OBJECT-TYPE
SYNTAX HwMonitorEntry
MAX-ACCESS not-accessible
                                             STATUS current
                                             DESCRIPTION
"/"
INDEX { hwMonIndex }
 ::= { hwMonitorTable 1 }

HwMonitorEntry ::= SEQUENCE {
hwMonIndex
 Integer32,
hwMonEquipId
 Unsigned32,
hwMonEquipName
 OCTET STRING,
hwMonEquipDescription
 OCTET STRING,
hwMonEquipSoftwareVersion
 OCTET STRING,
hwMonEquipPcbVersion
 OCTET STRING,
hwMonEquipManufacturer
 OCTET STRING,
hwMonEquipManuDate
 OCTET STRING,
hwMonEquipSerialNo
 OCTET STRING,
hwMonEquipOperTotalTime
 Unsigned32,
hwSetMonEquipCtrlState
 INTEGER,
hwCtrlMonEquipReset
 INTEGER,
hwMonitorOperStatus
 INTEGER,
hwMonRowStatus
 RowStatus
}

hwMonIndex OBJECT-TYPE
SYNTAX Integer32 (1..100)
MAX-ACCESS read-only
STATUS current
DESCRIPTION
"Table index of the site monitors (hwSiteMonitorTable) is restricted by the quantity of the site monitors (hwMonsQuantity). Value range: 1 to 100."
 ::= { hwMonitorEntry 1 }

hwMonEquipId OBJECT-TYPE
SYNTAX Unsigned32 (1001..1100)
MAX-ACCESS read-only
STATUS current
DESCRIPTION
"Site monitor ID. Value range: 001,001 to 001,100, in which the first three digits indicate the device type and the last three digits indicate the device SN. "
 ::= { hwMonitorEntry 2 }

hwMonEquipName OBJECT-TYPE
SYNTAX OCTET STRING (SIZE (0..63))
MAX-ACCESS read-write
STATUS current
DESCRIPTION
"Monitor name. It is of the character string type, and users can set the name of the monitor.   Otherwise, the configured character can not be any other languages except English."
 ::= { hwMonitorEntry 3 }

hwMonEquipDescription OBJECT-TYPE
SYNTAX OCTET STRING (SIZE (0..63))
MAX-ACCESS read-write
STATUS current
DESCRIPTION
"Monitor description. It is of the character string type. Users can set the description of the monitor. 
 Otherwise, the configured character can not be any other languages except English."
 ::= { hwMonitorEntry 4 }

hwMonEquipSoftwareVersion OBJECT-TYPE
SYNTAX OCTET STRING (SIZE (0..63))
MAX-ACCESS read-only
STATUS current
DESCRIPTION
"Monitor software version. It is of the character string type."
 ::= { hwMonitorEntry 5 }

hwMonEquipPcbVersion OBJECT-TYPE
SYNTAX OCTET STRING (SIZE (0..63))
MAX-ACCESS read-only
STATUS current
DESCRIPTION
"Monitor printed circuit board (PCB) hardware version. It is of the character string type."
 ::= { hwMonitorEntry 6 }

hwMonEquipManufacturer OBJECT-TYPE
SYNTAX OCTET STRING (SIZE (0..63))
MAX-ACCESS read-only
STATUS current
DESCRIPTION
"Monitor manufacture. It is of the character string type, and is an inherent attribute of the device."
 ::= { hwMonitorEntry 7 }

hwMonEquipManuDate OBJECT-TYPE
SYNTAX OCTET STRING (SIZE (0..127))
MAX-ACCESS read-only
STATUS current
DESCRIPTION
"Monitor production date. It is of the character string type, and is an inherent attribute of the device.  "
 ::= { hwMonitorEntry 8 }

hwMonEquipSerialNo OBJECT-TYPE
SYNTAX OCTET STRING (SIZE (0..127))
MAX-ACCESS read-only
STATUS current
DESCRIPTION
"Production SN of the monitor. It is the electronic tag of the products."
 ::= { hwMonitorEntry 9 }

hwMonEquipOperTotalTime OBJECT-TYPE
SYNTAX Unsigned32 (0..65535)
MAX-ACCESS read-only
STATUS current
DESCRIPTION
"Total monitor runtime. The monitor counts the data in real time. The value is an integer (.0), and unit is hour (h). It is used for performance measurement and evaluation of the monitor. Units:hours."
 ::= { hwMonitorEntry 10 }

hwSetMonEquipCtrlState OBJECT-TYPE
SYNTAX INTEGER
{
manualMode(1),
autoMode(2),
unknown(255)
}
MAX-ACCESS read-write
STATUS current
DESCRIPTION
"Monitor control status. It is an enumeration type:
  If the enumeration value is 1, it indicates the background control;
  If the enumeration value is 2, it indicates the automatic control.
  In manual state, monitor works under background commands; while monitors runs well automatically in auto state. 
  For details, see the corresponding user manual of the monitor."
 ::= { hwMonitorEntry 11 }

hwCtrlMonEquipReset OBJECT-TYPE
SYNTAX INTEGER
{
normal(1),
reset(2),
nullOper(255)
}
MAX-ACCESS read-write
STATUS current
DESCRIPTION
"Warm-reset control of the monitor. It is an enumeration type:
  If the network management system (NMS) notifies the SNMP agent that this node is set to 1, it indicates that the reset of the monitor is not triggered;
  If the NMS notifies the SNMP agent that this node is set to 2, it indicates that the background starts the reset of the monitor. "
 ::= { hwMonitorEntry 12 }

hwMonitorOperStatus OBJECT-TYPE
SYNTAX INTEGER
{
normal(1),
commRs485Fail(2),
commNetFail(3),
fault(4),
alarmResume(254),
other(255)
}
MAX-ACCESS read-only
STATUS current
DESCRIPTION
"State of the site monitor module. It is an enumeration type: 
  If the enumeration value is 1, it indicates that the site monitor module is in the normal state;
  If the enumeration value is 2, it indicates that the monitor module RS485 port communication failed; 
  If the enumeration value is 3, it indicates that the monitor module net port communication failed;  
  If the enumeration value is 4, it indicates that a fault occurs on the monitor module; 
  If the enumeration value is 254, it indicates monitor module alarm resume;  
  If the enumeration value is 255, it indicates monitor module operation status unknown. "
 ::= { hwMonitorEntry 99 }

hwMonRowStatus OBJECT-TYPE
SYNTAX RowStatus
MAX-ACCESS read-create
STATUS current
DESCRIPTION
"RowStatus of site monitor."
 ::= { hwMonitorEntry 100 }

hwSiteRectifiers OBJECT IDENTIFIER ::= { hwSiteMonitorMIBObjects 3 }

hwRectsGroup OBJECT IDENTIFIER ::= { hwSiteRectifiers 1 }

hwRectsGroupId OBJECT-TYPE
SYNTAX Unsigned32
MAX-ACCESS read-only
STATUS current
DESCRIPTION
"Device group ID of the rectifier module. It is the unique ID of the rectifier module group, and its default value: 002,000. 
  The first digits indicate the device type and the last three digits indicate the device SN. If the last three digits are 000, it indicates a virtual device. "
 ::= { hwRectsGroup 1 }

hwRectsGroupName OBJECT-TYPE
SYNTAX OCTET STRING (SIZE (0..63))
MAX-ACCESS read-write
STATUS current
DESCRIPTION
"Name of the rectifier module group, character string type, is used to specify the rectifier module group. Users can configure it.  Otherwise, the configured character can not be any other languages except English."
 ::= { hwRectsGroup 2 }

hwRectsTotalCurrent OBJECT-TYPE
SYNTAX Unsigned32 (0..200000)
MAX-ACCESS read-only
STATUS current
DESCRIPTION
"Total current of the rectifier module group on the site. It indicates the real-time statistics of the rectifier module group on the site. Default value: 0 to 20000, units: A, and the value is accurate to one decimal place (.1). 
 If the value is 2147483647(0x7FFFFFFF), it indicates that the value is invalid."
 ::= { hwRectsGroup 3 }

hwRectsTotalQuantity OBJECT-TYPE
SYNTAX Unsigned32 (0..256)
MAX-ACCESS read-only
STATUS current
DESCRIPTION
"Total quantity of the rectifier modules. Value range: 0 to 256. Units:pcs."
 ::= { hwRectsGroup 4 }

hwRectsRatedVoltage OBJECT-TYPE
SYNTAX Unsigned32 (420..583)
MAX-ACCESS read-only
STATUS current
DESCRIPTION
"Rated voltage of the rectifier module group. It is an inherent attribute. Value range: 42 to 58.3, Units: V, and the value is accurate to one decimal place (.1).  If the value is 2147483647(0x7FFFFFFF), it indicates that the value is invalid."
 ::= { hwRectsGroup 5 }

hwModifyRectsOutputVoltage OBJECT-TYPE
SYNTAX Unsigned32 (420..583)
MAX-ACCESS read-write
STATUS current
DESCRIPTION
"Voltage adjustment of the rectifier module, which users can configure it. Value range: 42 to 58.3, Units: V, and the value is accurate to one decimal space (.1). Based on the actual requirements, users can modify the output voltage of the rectifier module by modifying the value of the node. 
If the value is 2147483647(0x7FFFFFFF), it indicates that the value is invalid.
NOTES: Be cautious about changing the value of the node.  Only the system in manual mode, this parameter can be configured successfully."
 ::= { hwRectsGroup 6 }

hwSetRectsRedundEnable OBJECT-TYPE
SYNTAX INTEGER
{
disable(1),
enable(2),
funcNotSupport(3)
}
MAX-ACCESS read-write
STATUS current
DESCRIPTION
"Sleep function of the rectifier module group on the site. It is an enumeration value:If the NMS notifies the SNMP agent that this node is set to 1, it means to disable the sleep function of the rectifier module group;If the NMS notifies the SNMP agent that this node is set to 2, it means to enable the sleep function of the rectifier module group.If NMS get the node value is 3, it indicates that this function is not support, and in such case the value set to the agent is invalid.Default value: to disable the sleep function of the rectifier module group. For details, see the corresponding user manual of the monitor."
 ::= { hwRectsGroup 7 }

hwCtrlRectsAllOnOff OBJECT-TYPE
SYNTAX INTEGER
{
on(1),
off(2),
nullOper(255)
}
MAX-ACCESS read-write
STATUS current
DESCRIPTION
"Power-on or power-off of the rectifier module group (all the rectifier modules) on the site. It is an enumeration value:If the NMS notifies the SNMP agent that this node is set to 1, it indicates power-on of all rectifier modules;If the NMS notifies the SNMP agent that this node is set to 2, it indicates power-off of all the rectifier modules.
NOTE: Only the system in manual mode, this parameter can be configured successfully."
 ::= { hwRectsGroup 8 }

hwRectifier OBJECT IDENTIFIER ::= { hwSiteRectifiers 2 }

hwRectConfigTable OBJECT-TYPE
SYNTAX SEQUENCE OF HwRectConfigEntry
MAX-ACCESS not-accessible
                                             STATUS current
                                             DESCRIPTION
"Rectifier config information table. Use this table to get rectifiers equipment ID, software version, manufacturer, rated current, efficency, AC input type, and to control equipment on or off. This table's index is hwRectConfigIndex, clone Rectifier config information table."
 ::= { hwRectifier 1 }

hwRectConfigEntry OBJECT-TYPE
SYNTAX HwRectConfigEntry
MAX-ACCESS not-accessible
                                             STATUS current
                                             DESCRIPTION
"Rectifier config information table. Use this table to get rectifiers equipment ID, software version, manufacturer, rated current, efficency, AC input type, and to control equipment on or off. This table's index is hwRectConfigIndex, clone Rectifier config information table."
INDEX { hwRectConfigIndex }
 ::= { hwRectConfigTable 1 }

HwRectConfigEntry ::= SEQUENCE {
hwRectConfigIndex
 Integer32,
hwRectEquipId
 Unsigned32,
hwRectEquipName
 OCTET STRING,
hwRectType
 INTEGER,
hwRectSoftwareVersion
 OCTET STRING,
hwRectManufacturer
 OCTET STRING,
hwRectManuDate
 OCTET STRING,
hwRectSerialNo
 OCTET STRING,
hwRectRatedCurrent
 Unsigned32,
hwRectEfficency
 Unsigned32,
hwRectInputAcType
 INTEGER,
hwCtrlRectOnOff
 INTEGER,
hwRectConfigRowStatus
 RowStatus
}

hwRectConfigIndex OBJECT-TYPE
SYNTAX Integer32 (1..256)
MAX-ACCESS read-only
STATUS current
DESCRIPTION
"Index of the device configuration list for the rectifier modules, which value range: 1 to 256(To the actual subject). Lines of the device list are restricted by the total quantity of the rectifier modules (hwRectsTotalQuantity)."
 ::= { hwRectConfigEntry 1 }

hwRectEquipId OBJECT-TYPE
SYNTAX Unsigned32 (2001..2255)
MAX-ACCESS read-only
STATUS current
DESCRIPTION
"Rectifier module ID. Value range: 002'001 to 002'255. The first digits indicate the device type and last three digits indicate the device SN. "
 ::= { hwRectConfigEntry 2 }

hwRectEquipName OBJECT-TYPE
SYNTAX OCTET STRING (SIZE (0..63))
MAX-ACCESS read-write
STATUS current
DESCRIPTION
"Device name of the rectifier module, character string type, is used to specify the rectifier module. Users can configure it.  Otherwise, the configured character can not be any other languages except English."
 ::= { hwRectConfigEntry 3 }

hwRectType OBJECT-TYPE
SYNTAX INTEGER
{
eps5(1),
eps15(2),
eps30(3),
eps50(4),
eps100(5),
unknown(255)
}
MAX-ACCESS read-only
STATUS current
DESCRIPTION
"Specific type of the rectifier module. It is an enumeration type:
  If the enumeration value is 1, it indicates a 5A rectifier module; 
  If the enumeration value is 2, it indicates a 15A rectifier module; 
  If the enumeration value is 3, it indicates a 30A rectifier module; 
  If the enumeration value is 4, it indicates a 50A rectifier module; 
  If the enumeration value is 5, it indicates a 100A rectifier module."
 ::= { hwRectConfigEntry 4 }

hwRectSoftwareVersion OBJECT-TYPE
SYNTAX OCTET STRING (SIZE (0..63))
MAX-ACCESS read-only
STATUS current
DESCRIPTION
"Software version of the rectifier module. It indicates the software version ID of the module. "
 ::= { hwRectConfigEntry 5 }

hwRectManufacturer OBJECT-TYPE
SYNTAX OCTET STRING (SIZE (0..63))
MAX-ACCESS read-only
STATUS current
DESCRIPTION
"Manufacture of the rectifier module."
 ::= { hwRectConfigEntry 6 }

hwRectManuDate OBJECT-TYPE
SYNTAX OCTET STRING (SIZE (0..127))
MAX-ACCESS read-only
STATUS current
DESCRIPTION
"Manufacture date of rectifiers is of string type."
 ::= { hwRectConfigEntry 7 }

hwRectSerialNo OBJECT-TYPE
SYNTAX OCTET STRING (SIZE (0..127))
MAX-ACCESS read-only
STATUS current
DESCRIPTION
"Rectifier module SN. It indicates the electronic tag of the product."
 ::= { hwRectConfigEntry 8 }

hwRectRatedCurrent OBJECT-TYPE
SYNTAX Unsigned32 (0..2000)
MAX-ACCESS read-only
STATUS current
DESCRIPTION
"Rated voltage of the rectifier module, is an inherent attribute. Value range: 0 to 200, Units: A, and the value is accurate to one decimal place (.1). If the value is 2147483647(0x7FFFFFFF), it indicates that the value is invalid. "
 ::= { hwRectConfigEntry 9 }

hwRectEfficency OBJECT-TYPE
SYNTAX Unsigned32 (0..1000)
MAX-ACCESS read-only
STATUS current
DESCRIPTION
"Efficiency of the rectifier module, is an inherent attribute. Value range: 0 to 100, Units: %, and the value is accurate to one decimal place (.1). If the value is 2147483647(0x7FFFFFFF), it indicates that the value is invalid."
 ::= { hwRectConfigEntry 10 }

hwRectInputAcType OBJECT-TYPE
SYNTAX INTEGER
{
single(1),
triple(2),
threeLivelines(3),
unknown(255)
}
MAX-ACCESS read-only
STATUS current
DESCRIPTION
"Input AC type of the rectifier module. It is an enumeration value:
  If the value of the node is 1, it indicates single-phase AC input; 
  If the value of the node is 2, it indicates three-phase AC input;
 If the value of the node is 3, it indicates three-livelines AC input.  "
 ::= { hwRectConfigEntry 11 }

hwCtrlRectOnOff OBJECT-TYPE
SYNTAX INTEGER
{
on(1),
off(2),
nullOper(255)
}
MAX-ACCESS read-write
STATUS current
DESCRIPTION
"Power-on or power-off of the rectifier module, is an enumeration value. Users can modify the enumeration value of this node, thus controlling of the power-on or power-off of the rectifier module:
  If the NMS notifies the SNMP agent that this node is set to 1, it indicates power-on of the rectifier module;
  If the NMS notifies the SNMP agent that this node is set to 2, it indicates power-off of the rectifier module. "
 ::= { hwRectConfigEntry 12 }

hwRectConfigRowStatus OBJECT-TYPE
SYNTAX RowStatus
MAX-ACCESS read-create
STATUS current
DESCRIPTION
"RowStatus of rectifier config table."
 ::= { hwRectConfigEntry 100 }

hwRectOperTable OBJECT-TYPE
SYNTAX SEQUENCE OF HwRectOperEntry
MAX-ACCESS not-accessible
                                             STATUS current
                                             DESCRIPTION
"Rectifier runing information table. Use this table to get rectifiers output current, output voltage, totle runing time, and current run status. This table's index is hwRectRunIndex, clone rectifier runing information table."
 ::= { hwRectifier 2 }

hwRectOperEntry OBJECT-TYPE
SYNTAX HwRectOperEntry
MAX-ACCESS not-accessible
                                             STATUS current
                                             DESCRIPTION
"Rectifier runing information table. Use this table to get rectifiers output current, output voltage, totle runing time, and current run status. This table's index is hwRectRunIndex, clone rectifier runing information table."
INDEX { hwRectOperIndex }
 ::= { hwRectOperTable 1 }

HwRectOperEntry ::= SEQUENCE {
hwRectOperIndex
 Integer32,
hwRectOutputCurrent
 Unsigned32,
hwRectOutputVoltage
 Unsigned32,
hwRectTotalOperTime
 Unsigned32,
hwRectOperStatus
 INTEGER,
hwRectOperRowStatus
 RowStatus
}

hwRectOperIndex OBJECT-TYPE
SYNTAX Integer32 (1..256)
MAX-ACCESS read-only
STATUS current
DESCRIPTION
"Table index of the running rectifier modules, which value range: 1 to 256(To the actual subject). Lines of the device list are restricted by the total quantity of the rectifier modules (hwRectsTotalQuantity)."
 ::= { hwRectOperEntry 1 }

hwRectOutputCurrent OBJECT-TYPE
SYNTAX Unsigned32 (0..3000)
MAX-ACCESS read-only
STATUS current
DESCRIPTION
"Output current of the rectifier module. It is a real-time analog parameter. Value range: 0 to 300, Units: A, and the value is accurate to one decimal place (.1).  If the value is 2147483647(0x7FFFFFFF), it indicates that the value is invalid."
 ::= { hwRectOperEntry 2 }

hwRectOutputVoltage OBJECT-TYPE
SYNTAX Unsigned32 (0..650)
MAX-ACCESS read-only
STATUS current
DESCRIPTION
"Output voltage of the rectifier module. It is a real-time analog parameter. Value range: 0 to 65, Units: V, the value is accurate to one decimal place (.1). If the value is 2147483647(0x7FFFFFFF), it indicates that the value is invalid. "
 ::= { hwRectOperEntry 3 }

hwRectTotalOperTime OBJECT-TYPE
SYNTAX Unsigned32
MAX-ACCESS read-only
STATUS current
DESCRIPTION
"Total runtime of the rectifier module. Value units: minute (m), and the value is an integer (.0). "
 ::= { hwRectOperEntry 4 }

hwRectOperStatus OBJECT-TYPE
SYNTAX INTEGER
{
normal(1),
fault(2),
protect(3),
commFail(4),
switchOff(5),
invalid(6),
noConfig(7),
alarm(8),
acOff(9),
    rectLost(10),
alarmResume(254),
other(255)
}
MAX-ACCESS read-only
STATUS current
DESCRIPTION
"State of the rectifier module. It is an enumeration type: 
  If the enumeration value is 1, the rectifier module is in the normal state;
  If the enumeration value is 2, a fault occurs on the rectifier module; 
  If the enumeration value is 3, automatic protection of the rectifier module;
  If the enumeration value is 4, communication of the rectifier module fails;
  If the enumeration value is 5, the rectifier module is shut down; 
  If the enumeration value is 6, the rectifier module is invalid; 
  If the enumeration value is 7, this rectifier is not configured; 
 If the enumeration value is 8, this rectifier is alarm; 
If the enumeration value is 9, this rectifier is ac off;
If the enumeration value is 10, this rectifier is rectLost;
  If the enumeration value is 254, rectifier alarm resume; 
  If the enumeration value is 255, rectifier operation status unknown."
 ::= { hwRectOperEntry 99 }

hwRectOperRowStatus OBJECT-TYPE
SYNTAX RowStatus
MAX-ACCESS read-create
STATUS current
DESCRIPTION
"RowStatus of rectifier runing table."
 ::= { hwRectOperEntry 100 }

hwSiteBatterys OBJECT IDENTIFIER ::= { hwSiteMonitorMIBObjects 4 }

hwBattsConfig OBJECT IDENTIFIER ::= { hwSiteBatterys 1 }

hwBattsGroupId OBJECT-TYPE
SYNTAX Unsigned32
MAX-ACCESS read-only
STATUS current
DESCRIPTION
"Battery group ID. It is the unique ID of the battery group device. The first digits indicate the device type and the last three digits indicate the device SN. If the last three digits are 000, it indicates a virtual device. "
 ::= { hwBattsConfig 1 }

hwBattsGroupName OBJECT-TYPE
SYNTAX OCTET STRING (SIZE (0..63))
MAX-ACCESS read-write
STATUS current
DESCRIPTION
"Device name of the battery group. It is of the character string type, which can be configured by users. Otherwise, the configured character can not be any other languages except English."
 ::= { hwBattsConfig 2 }

hwBattsTotalQuantity OBJECT-TYPE
SYNTAX Unsigned32 (0..100)
MAX-ACCESS read-only
STATUS current
DESCRIPTION
"Total quantity of battery strings, which value range: 0 to 100. Units:strings."
 ::= { hwBattsConfig 3 }

hwSetBattsHighTempAction OBJECT-TYPE
SYNTAX INTEGER
{
blvd(1),
lowerDcOutput(2),
unknown(255)
}
MAX-ACCESS read-write
STATUS current
DESCRIPTION
"Battery high-temperature protection mode. It is an enumeration value, and can be configured. 
  If the enumeration value is 1, it indicates the power-off protection mode;
  If the enumeration value is 2, it indicates the protection mode of lowering the output voltage of the rectifier module. 
If the enumeration value is 255, it indicates do nothing. "
 ::= { hwBattsConfig 4 }

hwSetBattsHighTempVoltLimit OBJECT-TYPE
SYNTAX Unsigned32 (420..530)
MAX-ACCESS read-write
STATUS current
DESCRIPTION
"Battery protection voltage under high temperature. It works with the low-voltage power-off protection in battery high-temperature protection mode, which can be configured by users. If the low-voltage power-off protection mode (that is, the enumeration value is 1) is selected, the node is a low-voltage power-off node. Value range: 42 to 53, units: V, and the value is accurate to one decimal place (.1).  If the value is 2147483647(0x7FFFFFFF), it indicates that the value is invalid."
 ::= { hwBattsConfig 5 }

hwSetBattsHTDLimit OBJECT-TYPE
SYNTAX Integer32 (25..80)
MAX-ACCESS read-write
STATUS current
DESCRIPTION
"Upper threshold of the battery high temperature disconnection(HTD), can be configured by users. Value range: 25 to 80, Units: centigrade (°C), and the value is an integer (.0). If the value is 2147483647(0x7FFFFFFF), it indicates that the value is invalid.
NOTE: There is linkage between hwSetBattsHTDLimit and hwSetBattsTempUpperLimit"
 ::= { hwBattsConfig 6 }

hwSetBattsHTDEnable OBJECT-TYPE
SYNTAX INTEGER
{
enable(1),
disable(2)
}
MAX-ACCESS read-write
STATUS current
DESCRIPTION
"Battery high temperature disconnection enable. It is an enumeration type:
  If the enumeration value is 1, enable the operation of the battery disconnection in high temperature; 
  If the enumeration value is 2, disable the operation of the battery disconnection in high temperature. 
  The operation of the battery disconnection in high temperature is disabled by default. "
 ::= { hwBattsConfig 7 }

hwSetBattsFloatVoltage OBJECT-TYPE
SYNTAX Unsigned32 (420..583)
MAX-ACCESS read-write
STATUS current
DESCRIPTION
"Float charge voltage of the batteries, can be configured by users. Value range: 42 to 58.3, units: V, and the value is accurate to one decimal place (.1) If the value is 2147483647(0x7FFFFFFF), it indicates that the value is invalid.
NOTE: There is linkage between hwSetBattsFloatVoltage and hwSetBattsBoostVoltage
"
 ::= { hwBattsConfig 8 }

hwSetBattsBoostVoltage OBJECT-TYPE
SYNTAX Unsigned32 (420..583)
MAX-ACCESS read-write
STATUS current
DESCRIPTION
"Boostcharge voltage of the batteries, can be configured by users. Value range: 42 to 58.3, units: V, and the value is accurate to one decimal place (.1). If the value is 2147483647(0x7FFFFFFF), it indicates that the value is invalid.
NOTE: There is linkage between hwSetBattsFloatVoltage and hwSetBattsBoostVoltage"
 ::= { hwBattsConfig 9 }

hwSetBattsCurrLimitCoefficient OBJECT-TYPE
SYNTAX Unsigned32 (5..25)
MAX-ACCESS read-write
STATUS current
DESCRIPTION
"Current-limiting point coefficient of the batteries, can be configured by users. Value range: 0.05 to 0.25, units: C10, and the value is accurate to two decimal places (.2). If the value is 2147483647(0x7FFFFFFF), it indicates that the value is invalid."
 ::= { hwBattsConfig 10 }

hwSetBattsCompFactor OBJECT-TYPE
SYNTAX Unsigned32 (0..500)
MAX-ACCESS read-write
STATUS current
DESCRIPTION
"Temperature compensated coefficient of the batteries, can be configured by user. Value range: 0 to 500, units: mv per centigrade, and the value is an integer (.0). If the value is 2147483647(0x7FFFFFFF), it indicates that the value is invalid."
 ::= { hwBattsConfig 11 }

hwCtrlBattsBoostFloat OBJECT-TYPE
SYNTAX INTEGER
{
floatCharge(1),
boostCharge(2),
nullOper(255)
}
MAX-ACCESS read-write
STATUS current
DESCRIPTION
"Control batteries charge mode between boost and float. It is an enumeration value. 
  Users actively control the conversion. 
  If the NMS notifies the SNMP agent that this node is set to 1, it means to start the float charge mode of the batteries; 
  If the NMS notifies the SNMP agent that this node is set to 2, it means to start the boost charge mode of the batteries. "
 ::= { hwBattsConfig 12 }

hwSetBattsRatedCapacity OBJECT-TYPE
SYNTAX Unsigned32 (5..10000)
MAX-ACCESS read-write
STATUS current
DESCRIPTION
"Set batteries rated capacity. It is an analog parameter collected by the battery string in real time.Value range: 5 to 10000, units: Ah, the value is an integer (.0). If the value is 2147483647(0x7FFFFFFF), it indicates that the value is invalid."
 ::= { hwBattsConfig 13 }

hwBattsOperate OBJECT IDENTIFIER ::= { hwSiteBatterys 2 }

hwBattsTotalCurrent OBJECT-TYPE
SYNTAX Integer32 ( -400000..400000)
MAX-ACCESS read-only
STATUS current
DESCRIPTION
"Total current of the battery group. It indicates the real-time statistics of the battery group on the site. Value range: -40000 to +40000, units: A, and the value is accurate to one decimal place (.1).  If the value is 2147483647(0x7FFFFFFF), it indicates that the value is invalid."
 ::= { hwBattsOperate 1 }

hwBattsPreDischargeTime OBJECT-TYPE
SYNTAX Unsigned32 (0..15360)
MAX-ACCESS read-only
STATUS current
DESCRIPTION
"Battery group backup time. It indicates the real-time statistics of the battery group. Value range: 0 to 15360, Units: minute (m), and the value is an integer (.0).  If the value is 2147483647(0x7FFFFFFF), it indicates that the value is invalid."
 ::= { hwBattsOperate 2 }

hwBattsChargeStatus OBJECT-TYPE
SYNTAX INTEGER
{
floatCharge(1),
boostCharge(2),
disCharge(3),
hibernating(4),
unknown(255)
}
MAX-ACCESS read-only
STATUS current
DESCRIPTION
"Battery charging state, indicates the charging and discharging information about the battery group. It is an enumeration type. 
  If the enumeration value is 1, it indicates a battery group in the float charging state. 
  If the enumeration value is 2, it indicates a battery group in the boost charging state. 
  If the enumeration value is 3, it indicates a battery group in the discharging state. 
  If the enumeration value is 4, it indicates a battery group in the hibernating state. "
 ::= { hwBattsOperate 3 }

hwBattsCurrLimitStatus OBJECT-TYPE
SYNTAX INTEGER
{
unlimit(1),
limit(2),
unknown(255)
}
MAX-ACCESS read-only
STATUS current
DESCRIPTION
"Battery group current-limiting state, indicates the state information about the battery group. It is an enumeration value. 
  If the enumeration value is 1, it indicates that the current of the battery group is not limited. 
  If the enumeration value is 2, it indicates the current of the battery group is limited. "
 ::= { hwBattsOperate 4 }

hwBattsTemprature1 OBJECT-TYPE
SYNTAX Integer32 ( -50..100)
MAX-ACCESS read-only
STATUS current
DESCRIPTION
"Battery temperature. It is a battery parameter collected in real time. Value range: -50 to +100, unit: centigrade (degC), and the value is an integer (.1).
    If the value is 2147483647(0x7FFFFFFF), it indicates that battery temperature sensor is not configured."
 ::= { hwBattsOperate 5 }

hwBattsTemprature2 OBJECT-TYPE
SYNTAX Integer32 ( -50..100)
MAX-ACCESS read-only
STATUS current
DESCRIPTION
"Battery temperature. It is a battery parameter collected in real time. Value range: -50 to +100, unit: centigrade (degC), and the value is an integer (.1).
    If the value is 2147483647(0x7FFFFFFF), it indicates that battery temperature sensor is not configured."
 ::= { hwBattsOperate 6 }

hwBattsAlarmsClear OBJECT-TYPE
SYNTAX INTEGER
{
clearBattTestFailAlm(1),
clearBattTestCanceledAlm(2),
clearHighStrImpedanceAlm(3),
clearHighFloatCurrAlm(4),
clearCurrImbalanceAlm(5),
clearContactorFaultAlm(6),
nullOper(255)
}
MAX-ACCESS read-write
STATUS current
DESCRIPTION
"Battery alarms clear. It is an enumeration type:
  If the enumeration value is 1, it indicates the clear batt test fail alarm ;
  If the enumeration value is 2, it indicates the clear batt test canceled alarm .
  If the enumeration value is 3, it indicates the clear high str impedance alarm .
  If the enumeration value is 4, it indicates the clear high float current alarm .
  If the enumeration value is 5, it indicates the clear current imbalance alarm .
  If the enumeration value is 6, it indicates the clear contactor fault alarm .
  If the enumeration value is 255, it indicates null oper(can't set to smu)."
 ::= { hwBattsOperate 7 }

hwBattsTest OBJECT IDENTIFIER ::= { hwSiteBatterys 3 }

hwBattsTestRecordCount OBJECT-TYPE
SYNTAX Unsigned32 (0..100)
MAX-ACCESS read-only
STATUS current
DESCRIPTION
"Battery test records number."
 ::= { hwBattsTest 1 }

hwSetBattsManuStdTestTime OBJECT-TYPE
SYNTAX Unsigned32 (1..6000)
MAX-ACCESS read-write
STATUS current
DESCRIPTION
"Battery standard test time, It can be configured by users, and its value is an integer (.0). Here, if battery manual test is standard mode, value range defines between 1 to 6000, units: minutes(m). If the value is 2147483647(0x7FFFFFFF), it indicates that the value is invalid."
 ::= { hwBattsTest 2 }

hwSetBattsManuStdTestEndVolt OBJECT-TYPE
SYNTAX Unsigned32 (170..220)
MAX-ACCESS read-write
STATUS current
DESCRIPTION
"Voltage when the battery test is ended, can be configured by users. Units: V/cell, and the value is accurate to two decimal place (.2).  Here, if battery manual test is standard mode, value range defines between 1.7 to 2.2. If the value is 2147483647(0x7FFFFFFF), it indicates that the value is invalid."
 ::= { hwBattsTest 3 }

hwSetBattsManuStdTestCellNum OBJECT-TYPE
SYNTAX Unsigned32 (1..50)
MAX-ACCESS read-write
STATUS current
DESCRIPTION
"Battery cell number in each Group, which is used in the battery standard manual test, can be configured by users. Units: psc or cell, value range defines between 1 to 50. and the value is accurate to one decimal place (.0)."
 ::= { hwBattsTest 4 }

hwSetBattsManuShortTestTime OBJECT-TYPE
SYNTAX Unsigned32 (1..240)
MAX-ACCESS read-write
STATUS current
DESCRIPTION
"Battery short test time, It can be configured by users, and its value is an integer (.0).  If battery manual test is simple mode, value range defines between 1 to 240, units: minutes(m).  If the value is 2147483647(0x7FFFFFFF), it indicates that the value is invalid."
 ::= { hwBattsTest 5 }

hwSetBattsManuShortTestEndVolt OBJECT-TYPE
SYNTAX Unsigned32 (420..530)
MAX-ACCESS read-write
STATUS current
DESCRIPTION
"Voltage when the battery short test is ended, can be configured by users. Units: V, and the value is accurate to one decimal place (.1). Here, if battery manual test is standard mode, value range defines between 42 to 53.  If the value is 2147483647(0x7FFFFFFF), it indicates that the value is invalid."
 ::= { hwBattsTest 6 }

hwCtrlBattsTestStartStop OBJECT-TYPE
SYNTAX INTEGER
{
stdTestStart(1),
shortTestStart(2),
testStop(3),
nullOper(255)
}
MAX-ACCESS read-write
STATUS current
DESCRIPTION
"Battery manualtest start and stop. It is an enumeration value. 
  If the value is 1, it means to start a standard manual test; 
  If the value is 2, it means to start a short manual test; 
  If the value is 3, it means to stop the battery test.
If the value is 255, it means null operate(can't set to smu);  
  Set the parameters, such as battery test time, and voltage when the battery test stops before the node controls the start of the battery test. If the parameters are not set this time, the system uses the configuration parameters by default; and if the battery test is started at the first time, the system uses the default value. 
  Battery test can only start up in some conditions, so that the reason of Start of battery short test failed may be as follow:
  1. Interval between this test and the latest AC outage or test is longer than the preset duration.
  2. No major alarm is raised.
  3. The number of healthy modules is greater than 0.
  4. The number of battery strings is greater than 0."
 ::= { hwBattsTest 7 }

hwBattsTestResultTable OBJECT-TYPE
SYNTAX SEQUENCE OF HwBattsTestResultEntry
MAX-ACCESS not-accessible
                                             STATUS current
                                             DESCRIPTION
"Battery test result record table. Use this table to get battery test inital time, test result, battery efficiency, battery discharge time, terminated voltage, average current, discharge AH value, test temperature and test terminated course. This table's index is hwBattsTestResultIndex, clone Battery test result record table."
 ::= { hwBattsTest 100 }

hwBattsTestResultEntry OBJECT-TYPE
SYNTAX HwBattsTestResultEntry
MAX-ACCESS not-accessible
                                             STATUS current
                                             DESCRIPTION
"Battery test result record table. Use this table to get battery test inital time, test result, battery efficiency, battery discharge time, terminated voltage, average current, discharge AH value, test temperature and test terminated course. This table's index is hwBattsTestResultIndex, clone Battery test result record table."
INDEX { hwBattsTestResultIndex }
 ::= { hwBattsTestResultTable 1 }

HwBattsTestResultEntry ::= SEQUENCE {
hwBattsTestResultIndex
 Integer32,
hwBattsTestType
 INTEGER,
hwBattsTestStartTime
 OCTET STRING,
hwBattsTestResult
 INTEGER,
hwBattsEfficiency
 Integer32,
hwBattsDischargeTime
 Unsigned32,
hwBattsDischargeEndVoltage
 Unsigned32,
hwBattsDischargeAvCurrent
 Integer32,
hwBattsDischargeAhValue
 Unsigned32,
hwBattsTestTemprature
 Integer32,
hwBattsTestEndCourse
 INTEGER,
hwBattsTestResultRowStatus
 RowStatus
}

hwBattsTestResultIndex OBJECT-TYPE
SYNTAX Integer32 (1..100)
MAX-ACCESS read-only
STATUS current
DESCRIPTION
"Table index of the battery test results. Currently up to 10 times of the battery test results are saved by default. "
 ::= { hwBattsTestResultEntry 1 }

hwBattsTestType OBJECT-TYPE
SYNTAX INTEGER
{
manualTest(1),
acOffAutoTest(2),
timedTest(3),
shortTest(4),
other(255)
}
MAX-ACCESS read-only
STATUS current
DESCRIPTION
"Record test type of the battery test. It is an enumeration value: 
  If the NMS notifies the SNMP agent that this node is set to 1, it indicates a manual test; 
  If the NMS notifies the SNMP agent that this node is set to 2, it indicates a simplified test;
  If the NMS notifies the SNMP agent that this node is set to 3, it indicates a timed test;
  If the NMS notifies the SNMP agent that this node is set to 4, it indicates a short test;
  If the NMS notifies the SNMP agent that this node is set to 255, it indicates a other test."
 ::= { hwBattsTestResultEntry 2 }

hwBattsTestStartTime OBJECT-TYPE
SYNTAX OCTET STRING (SIZE (0..127))
MAX-ACCESS read-only
STATUS current
DESCRIPTION
"Test start time of the record in the battery test. It is of the character string type."
 ::= { hwBattsTestResultEntry 3 }

hwBattsTestResult OBJECT-TYPE
SYNTAX INTEGER
{
battNoResult(1),
battNormal(2),
battPreAlarm(3),
battAlarm(4),
unknown(255)
}
MAX-ACCESS read-only
STATUS current
DESCRIPTION
"Battery test result. It is an enumeration value.
  If the enumeration value of the node is 1, it indicates that the battery test has no result: 
  If the enumeration value of the node is 2, it indicates that the battery is in the normal state: 
  If the enumeration value of the node is 3, it indicates that the battery is in the minor abnormal state, 
  If the enumeration value of the node is 4, it indicates that the battery is in the alarm state,
  If the enumeration value of the node is 255, it indicates that the battery state is unknown,"
 ::= { hwBattsTestResultEntry 4 }

hwBattsEfficiency OBJECT-TYPE
SYNTAX Integer32 (0..100)
MAX-ACCESS read-only
STATUS current
DESCRIPTION
"Battery efficiency test. Value range: 0 to 100, Units: %, and the value is an integer (.0).
  If the value is -1, it indicates that the test value is inefficient.
  If the value is 255, it indicates that the test value is invalid."
 ::= { hwBattsTestResultEntry 5 }

hwBattsDischargeTime OBJECT-TYPE
SYNTAX Unsigned32 (0..10000)
MAX-ACCESS read-only
STATUS current
DESCRIPTION
"Discharge time of the battery test records. Value range: 0 to 100, units: hour (h), and the value is accurate to two decimal places (.2).  If the value is 2147483647(0x7FFFFFFF), it indicates that the value is invalid."
 ::= { hwBattsTestResultEntry 6 }

hwBattsDischargeEndVoltage OBJECT-TYPE
SYNTAX Unsigned32 (0..600)
MAX-ACCESS read-only
STATUS current
DESCRIPTION
"Discharge termination voltage of the battery test. Value range: 0 to 60, units: V, and the value is accurate to one decimal place (.1).  If the value is 2147483647(0x7FFFFFFF), it indicates that the value is invalid."
 ::= { hwBattsTestResultEntry 7 }

hwBattsDischargeAvCurrent OBJECT-TYPE
SYNTAX Integer32 ( -10000..10000)
MAX-ACCESS read-only
STATUS current
DESCRIPTION
"Average discharge current of the battery test. Value range: -1000 to 1000, units: A, and the value is accurate to one decimal place (.1).  If the value is 2147483647(0x7FFFFFFF), it indicates that the value is invalid."
 ::= { hwBattsTestResultEntry 8 }

hwBattsDischargeAhValue OBJECT-TYPE
SYNTAX Unsigned32 (0..5000)
MAX-ACCESS read-only
STATUS current
DESCRIPTION
"Discharge ampere per hour the battery test. Value range: 0 to 5000, Units: Ah, and the value is an integer (.0).   If the value is 2147483647(0x7FFFFFFF), it indicates that the value is invalid."
 ::= { hwBattsTestResultEntry 9 }

hwBattsTestTemprature OBJECT-TYPE
SYNTAX Integer32 ( -50..100)
MAX-ACCESS read-only
STATUS current
DESCRIPTION
"Battery temperature of the battery test termination. Value range: -50 to +100, Units: centigrade (°C), and the value is an integer (.0). If the value is -1024, it indicates that no battery temperature value sensor is detected."
 ::= { hwBattsTestResultEntry 10 }

hwBattsTestEndCourse OBJECT-TYPE
SYNTAX INTEGER
{
voltageToEnd(1),
timeToEnd(2),
acOnToEnd(3),
manulToEnd(4),
faultAlarmToEnd(5),
lowCapacityToEnd(6),
lowTempToEnd(7),
other(255)
}
MAX-ACCESS read-only
STATUS current
DESCRIPTION
"Termination factors of the battery test. It is an enumeration value. 
  If the enumeration value is 1, it indicates that the voltage value of the battery test reaches the set termination voltage; 
  If the enumeration value is 2, it indicates that the voltage value of the battery test reaches the timing limit; 
  If the enumeration value is 3, it indicates that an alarm related to the battery leads to the stop of the battery test; 
  If the enumeration value is 4, it indicates that a battery test is stopped manually,
  If the enumeration value is 5, it indicates that battery fault alarm happened,
If the enumeration value is 6, it indicates that battery low capacity happened,
If the enumeration value is 7, it indicates that battery low temp happened,
  If the enumeration value is 255, it indicates that battery test end for other courses."
 ::= { hwBattsTestResultEntry 11 }

hwBattsTestResultRowStatus OBJECT-TYPE
SYNTAX RowStatus
MAX-ACCESS read-create
STATUS current
DESCRIPTION
"RowStatus of battery test table."
 ::= { hwBattsTestResultEntry 100 }

hwBattString OBJECT IDENTIFIER ::= { hwSiteBatterys 4 }

hwBattStringConfigTable OBJECT-TYPE
SYNTAX SEQUENCE OF HwBattStringConfigEntry
MAX-ACCESS not-accessible
                                             STATUS current
                                             DESCRIPTION
"Battery string config table. Use this table to get battery string equipment ID and equipment name, to set battery standard capacity and battery install time as well. This table's index is hwBattStringConfigIndex, clone battery string config table."
 ::= { hwBattString 1 }

hwBattStringConfigEntry OBJECT-TYPE
SYNTAX HwBattStringConfigEntry
MAX-ACCESS not-accessible
                                             STATUS current
                                             DESCRIPTION
"Battery string config table. Use this table to get battery string equipment ID and equipment name, to set battery standard capacity and battery install time as well. This table's index is hwBattStringConfigIndex, clone battery string config table."
INDEX { hwBattStringConfigIndex }
 ::= { hwBattStringConfigTable 1 }

HwBattStringConfigEntry ::= SEQUENCE {
hwBattStringConfigIndex
 Integer32,
hwBattStringEquipId
 Unsigned32,
hwBattStringEquipName
 OCTET STRING,
hwSetBattsTempUpperLimit
 Integer32,
hwSetBattsTempLowerLimit
 Integer32,
hwSetBattsTempMeasureUpperLimit
 Integer32,
hwSetBattsTempMeasureLowerLimit
 Integer32,
hwSetBattStdCapacity
 Integer32,
hwSetBattInstallTime
 OCTET STRING,
hwBattStringConfigRowStatus
 RowStatus
}

hwBattStringConfigIndex OBJECT-TYPE
SYNTAX Integer32 (1..100)
MAX-ACCESS read-only
STATUS current
DESCRIPTION
"Device table index of the battery string,value range: 1 to 100(To the actual subject)."
 ::= { hwBattStringConfigEntry 1 }

hwBattStringEquipId OBJECT-TYPE
SYNTAX Unsigned32 (3001..3100)
MAX-ACCESS read-only
STATUS current
DESCRIPTION
"Batteries device ID, can be configured by users. Value range: 003,001 to 003,100, in which the first three digits specify the device type and the last three specify the device SN."
 ::= { hwBattStringConfigEntry 2 }

hwBattStringEquipName OBJECT-TYPE
SYNTAX OCTET STRING (SIZE (0..63))
MAX-ACCESS read-write
STATUS current
DESCRIPTION
"Batteries device name, of the character string type, is used to specify the batteries. Users can configure it. Otherwise, the configured character can not be any other languages except English."
 ::= { hwBattStringConfigEntry 3 }

hwSetBattsTempUpperLimit OBJECT-TYPE
SYNTAX Integer32 ( 25..80)
MAX-ACCESS read-write
STATUS current
DESCRIPTION
"Upper threshold of the battery temperature alarm, can be configured by users. Value range: 25 to 80, Units: centigrade (°C), and the value is an integer (.0).  If the value is 2147483647(0x7FFFFFFF), it indicates that the value is invalid.
NOTE: There is linkage between hwSetBattsHTDLimit and hwSetBattsTempUpperLimit"
 ::= { hwBattStringConfigEntry 4 }

hwSetBattsTempLowerLimit OBJECT-TYPE
SYNTAX Integer32 ( -20..20)
MAX-ACCESS read-write
STATUS current
DESCRIPTION
"Lower threshold of the battery temperature alarm, can be configured by users. Value range: -20 to 20, Units: centigrade (°C), and the value is an integer (.0).  If the value is 2147483647(0x7FFFFFFF), it indicates that the value is invalid."
 ::= { hwBattStringConfigEntry 5 }

hwSetBattsTempMeasureUpperLimit OBJECT-TYPE
SYNTAX Integer32 (0..100)
MAX-ACCESS read-write
STATUS current
DESCRIPTION
"Upper threshold of the battery temperature measurement, can be configured by users. Value range: 0 to 100, Units: centigrade (°C), and the value is an integer (.0).  If the value is 2147483647(0x7FFFFFFF), it indicates that the value is invalid."
 ::= { hwBattStringConfigEntry 6 }

hwSetBattsTempMeasureLowerLimit OBJECT-TYPE
SYNTAX Integer32 ( -50..0)
MAX-ACCESS read-write
STATUS current
DESCRIPTION
"Lower threshold of the battery temperature measurement, can be configured by users. Value range: -50 to 0, Units: centigrade (°C), and the value is an integer (.0).  If the value is 2147483647(0x7FFFFFFF), it indicates that the value is invalid."
 ::= { hwBattStringConfigEntry 7 }

hwSetBattStdCapacity OBJECT-TYPE
SYNTAX Integer32 (5..10000)
MAX-ACCESS read-write
STATUS current
DESCRIPTION
"Set battery standard capacity, is an inherent attribute of the device. Value range: 10 to 10000, units: Ah, the value is an integer (.0).   If the value is 2147483647(0x7FFFFFFF), it indicates that the value is invalid."
 ::= { hwBattStringConfigEntry 8 }

hwSetBattInstallTime OBJECT-TYPE
SYNTAX OCTET STRING (SIZE (0..128))
MAX-ACCESS read-write
STATUS current
DESCRIPTION
"Set battery install time, of the character string type, can be configured by users. Otherwise, the configured character can not be any other languages except English. "
 ::= { hwBattStringConfigEntry 9 }

hwBattStringConfigRowStatus OBJECT-TYPE
SYNTAX RowStatus
MAX-ACCESS read-create
STATUS current
DESCRIPTION
"RowStatus of battery string config table."
 ::= { hwBattStringConfigEntry 100 }

hwBattStringOperTable OBJECT-TYPE
SYNTAX SEQUENCE OF HwBattStringOperEntry
MAX-ACCESS not-accessible
                                             STATUS current
                                             DESCRIPTION
"Battery string runing table. Use this table to get battery string current, persent of remain capacity, battery remain capacity, battery actual capacity, as well as  battery temperature. This table's index is hwBattStringRunIndex, clone battery string runing table."
 ::= { hwBattString 2 }

hwBattStringOperEntry OBJECT-TYPE
SYNTAX HwBattStringOperEntry
MAX-ACCESS not-accessible
                                             STATUS current
                                             DESCRIPTION
"Battery string runing table. Use this table to get battery string current, persent of remain capacity, battery remain capacity, battery actual capacity, as well as  battery temperature. This table's index is hwBattStringRunIndex, clone battery string runing table."
INDEX { hwBattStringOperIndex }
 ::= { hwBattStringOperTable 1 }

HwBattStringOperEntry ::= SEQUENCE {
hwBattStringOperIndex
 Integer32,
hwBattStringCurrent
 Integer32,
hwBattStringRemainCapacityPercent
 Unsigned32,
hwBattStringRemainCapacity
 Unsigned32,
hwBattStringActualCapacity
 Unsigned32,
hwBattStringTemprature
 Integer32,
hwBattStringMidpointVoltage
 Integer32,
hwBattStringOperStatus
 INTEGER,
hwBattStringOperRowStatus
 RowStatus
}

hwBattStringOperIndex OBJECT-TYPE
SYNTAX Integer32 (1..100)
MAX-ACCESS read-only
STATUS current
DESCRIPTION
"Device table index of the battery string, which value range: 1 to 100,value range: 1 to 100(To the actual subject)."
 ::= { hwBattStringOperEntry 1 }

hwBattStringCurrent OBJECT-TYPE
SYNTAX Integer32 ( -10000..10000)
MAX-ACCESS read-only
STATUS current
DESCRIPTION
"Batteries current. It is an analog parameter collected by the battery string in real time. Value range: -1000 to +1000, units: A, and the value is accurate to one decimal place (.1).  If the value is 2147483647(0x7FFFFFFF), it indicates that the value is invalid."
 ::= { hwBattStringOperEntry 2 }

hwBattStringRemainCapacityPercent OBJECT-TYPE
SYNTAX Unsigned32 (0..1000)
MAX-ACCESS read-only
STATUS current
DESCRIPTION
"Remaining capacity percentage of the battery string. Value range: 0 to 100, units: %, and the value is accurate to one decimal place (.1).  If the value is 2147483647(0x7FFFFFFF), it indicates that the value is invalid."
 ::= { hwBattStringOperEntry 3 }

hwBattStringRemainCapacity OBJECT-TYPE
SYNTAX Unsigned32 (0..1000)
MAX-ACCESS read-only
STATUS current
DESCRIPTION
"Remaining capacity of the battery string. It is an analog parameter collected by the battery string in real time. Value range: 0 to 1000, units: Ah, and the value is an integer (.0).  If the value is 2147483647(0x7FFFFFFF), it indicates that the value is invalid."
 ::= { hwBattStringOperEntry 4 }

hwBattStringActualCapacity OBJECT-TYPE
SYNTAX Unsigned32 (0..5000)
MAX-ACCESS read-only
STATUS current
DESCRIPTION
"Batteries actual capacity. It is an analog parameter collected by the battery string in real time.Value range: 0 to 5000, units: Ah, the value is an integer (.0).  If the value is 2147483647(0x7FFFFFFF), it indicates that the value is invalid."
 ::= { hwBattStringOperEntry 5 }

hwBattStringTemprature OBJECT-TYPE
SYNTAX Integer32 ( -3000..2000)
MAX-ACCESS read-only
STATUS current
DESCRIPTION
"Battery temperature. It is a battery parameter collected in real time. Value range: -300 to +200, unit: centigrade (°C), and the value is an integer (.0).
  If the value is 2147483647(0x7FFFFFFF), it indicates that battery temperature sensor is not configured."
 ::= { hwBattStringOperEntry 6 }

hwBattStringMidpointVoltage OBJECT-TYPE
SYNTAX Integer32 ( -650..650)
MAX-ACCESS read-only
STATUS current
DESCRIPTION
"Batteries midpoint voltage. It is an analog parameter collected by the battery string in real time. Value range: 0 to +650, unit: V, and the value is accurate to one decimal place (.1)."
 ::= { hwBattStringOperEntry 7 }

hwBattStringOperStatus OBJECT-TYPE
SYNTAX INTEGER
{
normal(1),
tempHigh(2),
tempLow(3),
loopBreak(4),
overCurrent(5),
unbalance(6),
discharge(7),
fuseBreak(8),
alarmResume(254),
other(255)
}
MAX-ACCESS read-only
STATUS current
DESCRIPTION
"State of the site battery string module. It is an enumeration type: 
  If the enumeration value is 1, it indicates that the site battery string is in the normal state; 
  If the enumeration value is 2, it indicates that the battery string is over upper alarm threshold of temperature; 
  If the enumeration value is 3, it indicates that the battery string is under lower alarm threshold of temperature;  
  If the enumeration value is 4, it indicates that battery string loop has disconnected;  
  If the enumeration value is 5, it indicates that the current of batery is over upper charging threshold;
  If the enumeration value is 6, it indicates that the battery string is unbalance;  
  If the enumeration value is 7, it indicates that battery string is discharge;  
  If the enumeration value is 8, it indicates that battery string is fuseBreak;
  If the enumeration value is 254, it indicates battery string alarm resume; 
  If the enumeration value is 255, it indicates battery string operation status unknown. "
 ::= { hwBattStringOperEntry 99 }

hwBattStringOperRowStatus OBJECT-TYPE
SYNTAX RowStatus
MAX-ACCESS read-create
STATUS current
DESCRIPTION
"RowStatus of battery string runing table."
 ::= { hwBattStringOperEntry 100 }

hwSiteAcDistributions OBJECT IDENTIFIER ::= { hwSiteMonitorMIBObjects 5 }

hwAcDistributionsGroup OBJECT IDENTIFIER ::= { hwSiteAcDistributions 1 }

hwAcsGroupId OBJECT-TYPE
SYNTAX Unsigned32
MAX-ACCESS read-only
STATUS current
DESCRIPTION
"AC group ID, is the unique ID of the AC group. The first three digits indicate the device type and the last three indicate the device SN. If the last three digits are 000, it indicates a virtual device. "
 ::= { hwAcDistributionsGroup 1 }

hwAcsGroupName OBJECT-TYPE
SYNTAX OCTET STRING (SIZE (0..63))
MAX-ACCESS read-write
STATUS current
DESCRIPTION
"Device name of the AC group. It is of the character string type, and can be configured by users. Otherwise, the configured character can not be any other languages except English."
 ::= { hwAcDistributionsGroup 2 }

hwAcsTotalCurrent OBJECT-TYPE
SYNTAX Unsigned32 (0..10000)
MAX-ACCESS read-only
STATUS current
DESCRIPTION
"Total current of the AC group. It indicates the real-time statistics of the AC group. Value range: 0 to 1000, units: A, and the value is accurate to one decimal place (.1). If the value is 2147483647(0x7FFFFFFF), it indicates that the value is invalid."
 ::= { hwAcDistributionsGroup 3 }

hwAcsTotalQuantity OBJECT-TYPE
SYNTAX Unsigned32 (0..100)
MAX-ACCESS read-only
STATUS current
DESCRIPTION
"Total quantity of the site ACUs. Value range: 0 to 100. "
 ::= { hwAcDistributionsGroup 4 }

hwSetAcsUpperVoltLimit OBJECT-TYPE
SYNTAX Unsigned32 (50..600)
MAX-ACCESS read-write
STATUS current
DESCRIPTION
"Upper threshold of the AC voltage alarm, can be configured by users. Value range: 50 to 600, units: V, and the value is an integer (.0).  If the value is 2147483647(0x7FFFFFFF), it indicates that the value is invalid.
NOTE: There is linkage between hwSetAcsUpperVoltLimit and hwSetAcsLowerVoltLimit"
 ::= { hwAcDistributionsGroup 5 }

hwSetAcsLowerVoltLimit OBJECT-TYPE
SYNTAX Unsigned32 (50..600)
MAX-ACCESS read-write
STATUS current
DESCRIPTION
"Lower threshold of the AC voltage alarm, can be configured by users. Value range: 50 to 600, units: V, and the value is an integer (.0).  If the value is 2147483647(0x7FFFFFFF), it indicates that the value is invalid.
NOTE: There is linkage between hwSetAcsUpperVoltLimit and hwSetAcsLowerVoltLimit"
 ::= { hwAcDistributionsGroup 6 }

hwAcsPerfoGenera OBJECT-TYPE
SYNTAX Unsigned32 (0..1000000)
MAX-ACCESS read-only
STATUS current
DESCRIPTION
"Perfo genera of the AC. Value range: 0 to 10000, units:KWh ,the value is accurate to two decimal place (.2). If the value is 2147483647(0x7FFFFFFF), it indicates that the value is invalid."
 ::= { hwAcDistributionsGroup 7 }

hwAcDistribution OBJECT IDENTIFIER ::= { hwSiteAcDistributions 2 }

hwAcInputTable OBJECT-TYPE
SYNTAX SEQUENCE OF HwAcInputEntry
MAX-ACCESS not-accessible
                                             STATUS current
                                             DESCRIPTION
"AC input table. Use this table to get AC distribution unit ID, AC distribution unit name, A phase or AB line voltage, B phase or BC line voltage, C phase or CA line voltage, AC input breaker status, as well as AC output breakers quantity, which defines hwAcOutputBreakerTable row number. This table's index is hwAcInputIndex, clone AC input table."
 ::= { hwAcDistribution 1 }

hwAcInputEntry OBJECT-TYPE
SYNTAX HwAcInputEntry
MAX-ACCESS not-accessible
                                             STATUS current
                                             DESCRIPTION
"AC input table. Use this table to get AC distribution unit ID, AC distribution unit name, A phase or AB line voltage, B phase or BC line voltage, C phase or CA line voltage, AC input breaker status, as well as AC output breakers quantity, which defines hwAcOutputBreakerTable row number. This table's index is hwAcInputIndex, clone AC input table."
INDEX { hwAcInputIndex }
 ::= { hwAcInputTable 1 }

HwAcInputEntry ::= SEQUENCE {
hwAcInputIndex
 Integer32,
hwAcEquipId
 Unsigned32,
hwAcEquipName
 OCTET STRING,
hwApOrAblVoltage
 Unsigned32,
hwBpOrBclVoltage
 Unsigned32,
hwCpOrCalVoltage
 Unsigned32,
hwAphaseCurrent
 Integer32,
hwBphaseCurrent
 Integer32,
hwCphaseCurrent
 Integer32,
hwAcInputBreakersQuantity
 Unsigned32,
hwAcInputOperStatus
 INTEGER,
hwAcRowStatus
 RowStatus
}

hwAcInputIndex OBJECT-TYPE
SYNTAX Integer32 (1..100)
MAX-ACCESS read-only
STATUS current
DESCRIPTION
"ACU device table index, which value range: 1 to 100. Lines of the device list are restricted by the total quantity of ACUs (hwAcsInputQuantity)."
 ::= { hwAcInputEntry 1 }

hwAcEquipId OBJECT-TYPE
SYNTAX Unsigned32 (4001..4100)
MAX-ACCESS read-only
STATUS current
DESCRIPTION
"ACU device ID, which users can configure. Value range: 004,001 to 004,100, in which The first digits indicate the device type and the last three digits indicate the device SN."
 ::= { hwAcInputEntry 2 }

hwAcEquipName OBJECT-TYPE
SYNTAX OCTET STRING (SIZE (0..63))
MAX-ACCESS read-write
STATUS current
DESCRIPTION
"ACU device name, of the character string type, is used to specify the alternating current unit (ACU). Users can configure it. Otherwise, the configured character can not be any other languages except English."
 ::= { hwAcInputEntry 3 }

hwApOrAblVoltage OBJECT-TYPE
SYNTAX Unsigned32 (0..5000)
MAX-ACCESS read-only
STATUS current
DESCRIPTION
"ACU A-phase or AB-line voltage. Value range: 0 to 500, units: V, and the value is accurate to one decimal place (.1).  If the value is 2147483647(0x7FFFFFFF), it indicates that the value is invalid."
 ::= { hwAcInputEntry 4 }

hwBpOrBclVoltage OBJECT-TYPE
SYNTAX Unsigned32 (0..5000)
MAX-ACCESS read-only
STATUS current
DESCRIPTION
"ACU B-phase or BC-line voltage. Value range: 0 to 500, units: V, and the value is accurate to one decimal place (.1).  If the value is 2147483647(0x7FFFFFFF), it indicates that the value is invalid."
 ::= { hwAcInputEntry 5 }

hwCpOrCalVoltage OBJECT-TYPE
SYNTAX Unsigned32 (0..5000)
MAX-ACCESS read-only
STATUS current
DESCRIPTION
"ACU C-phase or CA-line voltage. Value range: 0 to 500, units: V, and the value is accurate to one decimal place (.1).  If the value is 2147483647(0x7FFFFFFF), it indicates that the value is invalid."
 ::= { hwAcInputEntry 6 }

hwAphaseCurrent OBJECT-TYPE
SYNTAX Integer32 (0..1000)
MAX-ACCESS read-only
STATUS current
DESCRIPTION
"ACU A-phase current. It is an analog parameter collected by the ACU in real time. Value range: 0 to 100, units: A, and the value is accurate to one decimal place (.1).  If the value is 2147483647(0x7FFFFFFF), it indicates that the value is invalid."
 ::= { hwAcInputEntry 7 }

hwBphaseCurrent OBJECT-TYPE
SYNTAX Integer32 (0..1000)
MAX-ACCESS read-only
STATUS current
DESCRIPTION
"ACU B-phase current. It is an analog parameter collected by the ACU in real time. Value range: 0 to 100, units: A, and the value is accurate to one decimal place (.1).  If the value is 2147483647(0x7FFFFFFF), it indicates that the value is invalid."
 ::= { hwAcInputEntry 8 }

hwCphaseCurrent OBJECT-TYPE
SYNTAX Integer32 (0..1000)
MAX-ACCESS read-only
STATUS current
DESCRIPTION
"ACU C-phase current. It is an analog parameter collected by the ACU in real time. Value range: 0 to 100, units: A, and the value is accurate to one decimal place (.1).  If the value is 2147483647(0x7FFFFFFF), it indicates that the value is invalid."
 ::= { hwAcInputEntry 9 }

hwAcInputBreakersQuantity OBJECT-TYPE
SYNTAX Unsigned32 (0..100)
MAX-ACCESS read-only
STATUS current
DESCRIPTION
"Quantity of the AC air circuit breakers. As the ACU lower-level subset, the node indicates the quantity of the output air circuit breakers contained by each ACU lower-level subset. Value range: 0 to 100. "
 ::= { hwAcInputEntry 10 }

hwAcInputOperStatus OBJECT-TYPE
SYNTAX INTEGER
{
normal(1),
acOff(2),
acAbsent(3),
voltHigh(4),
voltLow(5),
 freqHigh(6),
freqLow(7),
alarmResume(254),
other(255)
}
MAX-ACCESS read-only
STATUS current
DESCRIPTION
"State of the site AC distribution uint. It is an enumeration type: 
  If the enumeration value is 1, it indicates that the site AC distribution uint is in the normal state; 
  If the enumeration value is 2, it indicates that AC distribution uint power off; 
  If the enumeration value is 3, it indicates that AC input phase absent;
  If the enumeration value is 4, it indicates that AC voltage is over upper alarm threshold;  
  If the enumeration value is 5, it indicates that AC voltage is under lower alarm threshold;  
  If the enumeration value is 6, it indicates that AC voltage is freqHigh;  
  If the enumeration value is 7, it indicates that AC voltage is freqLow;  
  If the enumeration value is 254, it indicates AC distribution uint alarm resume; 
  If the enumeration value is 255, it indicates AC distribution uint operation status unknown. "
 ::= { hwAcInputEntry 99 }

hwAcRowStatus OBJECT-TYPE
SYNTAX RowStatus
MAX-ACCESS read-create
STATUS current
DESCRIPTION
"RowStatus of ACU."
 ::= { hwAcInputEntry 100 }

hwAcInputBreakerTable OBJECT-TYPE
SYNTAX SEQUENCE OF HwAcInputBreakerEntry
MAX-ACCESS not-accessible
                                             STATUS current
                                             DESCRIPTION
"Ac input breaker table. Use this table to get AC input breaker equipment ID, AC input breaker equipment name, and AC input breaker status. This table's index is hwAcInputBreakerIndex, which qualificated by hwAcInputBreakersQuantity in hwAcInputTable, clone Ac input breaker table."
 ::= { hwAcDistribution 2 }

hwAcInputBreakerEntry OBJECT-TYPE
SYNTAX HwAcInputBreakerEntry
MAX-ACCESS not-accessible
                                             STATUS current
                                             DESCRIPTION
"Ac input breaker table. Use this table to get AC input breaker equipment ID, AC input breaker equipment name, and AC input breaker status. This table's index is hwAcInputBreakerIndex, which qualificated by hwAcInputBreakersQuantity in hwAcInputTable, clone Ac input breaker table."
INDEX { hwAcInputBreakerIndex }
 ::= { hwAcInputBreakerTable 1 }

HwAcInputBreakerEntry ::= SEQUENCE {
hwAcInputBreakerIndex
 Integer32,
hwAcInputBreakerEquipId
 Unsigned32,
hwAcInputBreakerEquipName
 OCTET STRING,
hwAcInputBreakerOperStatus
 INTEGER,
hwAcInputBreakerRowStatus
 RowStatus
}

hwAcInputBreakerIndex OBJECT-TYPE
SYNTAX Integer32 (1..100)
MAX-ACCESS read-only
STATUS current
DESCRIPTION
"Device table index of the AC air circuit breaker. Value range: 1 to 100. An input air circuit breaker device can be uniquely identified through the ACU table index and device index of the AC air circuit breaker.  "
 ::= { hwAcInputBreakerEntry 1 }

hwAcInputBreakerEquipId OBJECT-TYPE
SYNTAX Unsigned32 (5001..5100)
MAX-ACCESS read-only
STATUS current
DESCRIPTION
"AC input air circuit breaker ID. Value range: 005,001 to 005,100. The first digits indicate the device type and the last three digits indicate the device SN."
 ::= { hwAcInputBreakerEntry 2 }

hwAcInputBreakerEquipName OBJECT-TYPE
SYNTAX OCTET STRING (SIZE (0..63))
MAX-ACCESS read-write
STATUS current
DESCRIPTION
"AC input air circuit breaker name, of the character string type, can configured by users. Otherwise, the configured character can not be any other languages except English."
 ::= { hwAcInputBreakerEntry 3 }

hwAcInputBreakerOperStatus OBJECT-TYPE
SYNTAX INTEGER
{
normal(1),
disconnect(2),
alarmResume(254),
other(255)
}
MAX-ACCESS read-only
STATUS current
DESCRIPTION
"Operation state of the site AC input breaker. It is an enumeration type: 
  If the enumeration value is 1, it indicates that the site AC input breaker is in the normal state; 
  If the enumeration value is 2, it indicates that the AC input breaker disconnect; 
  If the enumeration value is 254, it indicates AC input breaker alarm resume; 
  If the enumeration value is 255, it indicates AC input breaker operation status unknown. "
 ::= { hwAcInputBreakerEntry 99 }

hwAcInputBreakerRowStatus OBJECT-TYPE
SYNTAX RowStatus
MAX-ACCESS read-create
STATUS current
DESCRIPTION
"RowStatus of AC input breaker."
 ::= { hwAcInputBreakerEntry 100 }

hwSiteDcDistributions OBJECT IDENTIFIER ::= { hwSiteMonitorMIBObjects 6 }

hwDcDistributionsGroup OBJECT IDENTIFIER ::= { hwSiteDcDistributions 1 }

hwDcsGroupId OBJECT-TYPE
SYNTAX Unsigned32
MAX-ACCESS read-only
STATUS current
DESCRIPTION
"DC group ID: unique ID of the DC group. in which The first digits indicate the device type and the last three digits indicate the device SN. If the last three digits are 000, it indicates a virtual device."
 ::= { hwDcDistributionsGroup 1 }

hwDcsGroupName OBJECT-TYPE
SYNTAX OCTET STRING (SIZE (0..63))
MAX-ACCESS read-write
STATUS current
DESCRIPTION
"Device name of the DC group, of the character string type, can be configured by users. Otherwise, the configured character can not be any other languages except English."
 ::= { hwDcDistributionsGroup 2 }

hwDcsTotalVoltage OBJECT-TYPE
SYNTAX Unsigned32 (0..1000)
MAX-ACCESS read-only
STATUS current
DESCRIPTION
"Total voltage of the DC group. Value range: 0 to 100, units: V, and the value is accurate to one decimal place (.1).  If the value is 2147483647(0x7FFFFFFF), it indicates that the value is invalid."
 ::= { hwDcDistributionsGroup 3 }

hwDcsTotalCurrent OBJECT-TYPE
SYNTAX Integer32 ( -300000..300000)
MAX-ACCESS read-only
STATUS current
DESCRIPTION
"Total current of the DC group. Value range: -30000 to 30000, units: A, and the value is accurate to one decimal place (.1).   If the value is 2147483647(0x7FFFFFFF), it indicates that the value is invalid."
 ::= { hwDcDistributionsGroup 4 }

hwDcsTotalPower OBJECT-TYPE
SYNTAX Unsigned32 (0..3000000)
MAX-ACCESS read-only
STATUS current
DESCRIPTION
"Total power of the DC group. Value range: 0 to 3000000, units: W, and the value is an integer (.0).  If the value is 2147483647(0x7FFFFFFF), it indicates that the value is invalid."
 ::= { hwDcDistributionsGroup 5 }

hwDcsTotalQuantity OBJECT-TYPE
SYNTAX Unsigned32 (0..100)
MAX-ACCESS read-only
STATUS current
DESCRIPTION
"Total quantity of the DC units, and its Value range: 0 to 100."
 ::= { hwDcDistributionsGroup 6 }

hwSetDcsUpperVoltLimit OBJECT-TYPE
SYNTAX Unsigned32 (530..600)
MAX-ACCESS read-write
STATUS current
DESCRIPTION
"Upper threshold of the DC voltage alarm, can be configued by users. Value range: 53 to 60, units: V, and the value is accurate to one decimal space (.1).  If the value is 2147483647(0x7FFFFFFF), it indicates that the value is invalid.
NOTE: There is linkage between hwSetDcsUpperVoltLimit and hwSetDcsLowerVoltLimit"
 ::= { hwDcDistributionsGroup 7 }

hwSetDcsLowerVoltLimit OBJECT-TYPE
SYNTAX Unsigned32 (350..570)
MAX-ACCESS read-write
STATUS current
DESCRIPTION
"Lower threshold of the DC voltage alarm, can be configued by users. Value range: 35 to 57, units: V, and the value is accurate to one decimal space (.1).  If the value is 2147483647(0x7FFFFFFF), it indicates that the value is invalid.
NOTE: There is linkage between hwSetDcsUpperVoltLimit and hwSetDcsLowerVoltLimit"
 ::= { hwDcDistributionsGroup 8 }

hwDcsPerfoLoadConsume OBJECT-TYPE
SYNTAX Unsigned32 (0..10000)
MAX-ACCESS read-only
STATUS current
DESCRIPTION
"PerfoLoad Consume of the DC,Value range: 0 to 10000, units: KWh, and the value is accurate to one decimal space (.0).  If the value is 2147483647(0x7FFFFFFF), it indicates that the value is invalid."
 ::= { hwDcDistributionsGroup 9 }

hwDcDistribution OBJECT IDENTIFIER ::= { hwSiteDcDistributions 2 }

hwDcOutputTable OBJECT-TYPE
SYNTAX SEQUENCE OF HwDcOutputEntry
MAX-ACCESS not-accessible
                                             STATUS current
                                             DESCRIPTION
"/"
 ::= { hwDcDistribution 1 }

hwDcOutputEntry OBJECT-TYPE
SYNTAX HwDcOutputEntry
MAX-ACCESS not-accessible
                                             STATUS current
                                             DESCRIPTION
"/"
INDEX { hwDcOutputIndex }
 ::= { hwDcOutputTable 1 }

HwDcOutputEntry ::= SEQUENCE {
hwDcOutputIndex
 Integer32,
hwDcOutputEquipId
 Unsigned32,
hwDcOutputEquipName
 OCTET STRING,
hwDcOutputVoltage
 Unsigned32,
hwDcOutputCurrent
 Integer32,
hwDcOutputPower
 Unsigned32,
hwLoadsQuantity
 Unsigned32,
hwDcOutputOperStatus
 INTEGER,
hwDcOutputRowStatus
 RowStatus
}

hwDcOutputIndex OBJECT-TYPE
SYNTAX Integer32 (1..100)
MAX-ACCESS read-only
STATUS current
DESCRIPTION
"Device table index of the DC units, which value range: 1 to 100. Lines of the device list are restricted by the total quantity of DC units (hwDcsQuantity)."
 ::= { hwDcOutputEntry 1 }

hwDcOutputEquipId OBJECT-TYPE
SYNTAX Unsigned32 (6001..6100)
MAX-ACCESS read-only
STATUS current
DESCRIPTION
"DC unit device ID, which value range: 006,001 to 006,100. The first digits indicate the device type and the last three digits indicate the device SN. "
 ::= { hwDcOutputEntry 2 }

hwDcOutputEquipName OBJECT-TYPE
SYNTAX OCTET STRING (SIZE (0..63))
MAX-ACCESS read-write
STATUS current
DESCRIPTION
"DC unit device name, of the character string type, can be configued by users.  Otherwise, the configured character can not be any other languages except English."
 ::= { hwDcOutputEntry 3 }

hwDcOutputVoltage OBJECT-TYPE
SYNTAX Unsigned32 (0..1000)
MAX-ACCESS read-only
STATUS current
DESCRIPTION
"DC output voltage. It is an analog parameter collected by the DC power in real time. Value range: 0 to 100, units: V, and the value is accurate to one decimal space (.1).  If the value is 2147483647(0x7FFFFFFF), it indicates that the value is invalid."
 ::= { hwDcOutputEntry 4 }

hwDcOutputCurrent OBJECT-TYPE
SYNTAX Integer32 ( -300000..300000)
MAX-ACCESS read-only
STATUS current
DESCRIPTION
"DC output current. It is an analog parameter collected by the DC power in real time. Value range: -30000 to 30000, units: A, and the value is accurate to one decimal space (.1). If the value is 2147483647(0x7FFFFFFF), it indicates that the value is invalid."
 ::= { hwDcOutputEntry 5 }

hwDcOutputPower OBJECT-TYPE
SYNTAX Unsigned32 (0..3000000)
MAX-ACCESS read-only
STATUS current
DESCRIPTION
"DC output power. It is an analog parameter collected by the DC power in real time. Value range: 0 to 3000000, units: W, and the value is an integer (.0).  If the value is 2147483647(0x7FFFFFFF), it indicates that the value is invalid."
 ::= { hwDcOutputEntry 6 }

hwLoadsQuantity OBJECT-TYPE
SYNTAX Unsigned32 (0..100)
MAX-ACCESS read-only
STATUS current
DESCRIPTION
"Quantity of the DC load output branches, which value range: 0 to 100.  As the DC unit lower-level subset, the node indicates the quantity of the DC load output branches contained by each DC unit lower-level subset."
 ::= { hwDcOutputEntry 7 }

hwDcOutputOperStatus OBJECT-TYPE
SYNTAX INTEGER
{
normal(1),
voltHigh(2),
voltLow(3),
dcAbsent(4),
overload(5),
alarmResume(254),
other(255)
}
MAX-ACCESS read-only
STATUS current
DESCRIPTION
"State of the site DC distribution uint. It is an enumeration type: 
  If the enumeration value is 1, it indicates that the site DC distribution uint is in the normal state; 
  If the enumeration value is 2, it indicates that DC voltage is over the upper alarm threshold;
  If the enumeration value is 3, it indicates that DC voltage is under the lower alarm threshold; 
If the enumeration value is 4, it indicates that DC voltage is dcAbsent; 
If the enumeration value is 5, it indicates that DC voltage is overload; 
  If the enumeration value is 254, it indicates DC distribution uint alarm resume; 
  If the enumeration value is 255, it indicates DC distribution uint operation status unknown. "
 ::= { hwDcOutputEntry 99 }

hwDcOutputRowStatus OBJECT-TYPE
SYNTAX RowStatus
MAX-ACCESS read-create
STATUS current
DESCRIPTION
"RowStatus of Dc output equipments."
 ::= { hwDcOutputEntry 100 }

hwLoadBranchTable OBJECT-TYPE
SYNTAX SEQUENCE OF HwLoadBranchEntry
MAX-ACCESS not-accessible
                                             STATUS current
                                             DESCRIPTION
"Loads output table. Use this table to get load branch equipment ID, load branch equipment name, load branch current, and load branch power. This table's index is hwLoadBranchIndex, which qualificated by hwloadsQuantity in hwDcOutputTable, clone loads output table."
 ::= { hwDcDistribution 2 }

hwLoadBranchEntry OBJECT-TYPE
SYNTAX HwLoadBranchEntry
MAX-ACCESS not-accessible
                                             STATUS current
                                             DESCRIPTION
"Loads output table. Use this table to get load branch equipment ID, load branch equipment name, load branch current, and load branch power. This table's index is hwLoadBranchIndex, which qualificated by hwloadsQuantity in hwDcOutputTable, clone loads output table."
INDEX { hwLoadBranchIndex }
 ::= { hwLoadBranchTable 1 }

HwLoadBranchEntry ::= SEQUENCE {
hwLoadBranchIndex
 Integer32,
hwLoadBranchEquipId
 Unsigned32,
hwLoadBranchEquipName
 OCTET STRING,
hwLoadBranchCurrent
 Unsigned32,
hwLoadBranchPower
 Unsigned32,
hwLoadBranchOperStatus
 INTEGER,
hwLoadBranchRowStatus
 RowStatus
}

hwLoadBranchIndex OBJECT-TYPE
SYNTAX Integer32 (1..100)
MAX-ACCESS read-only
STATUS current
DESCRIPTION
"Device table index of the DC load output branch, which value range: 1 to 100.  A DC load output branch can be uniquely identified through the DC unit table index and device index of the DC load output branch."
 ::= { hwLoadBranchEntry 1 }

hwLoadBranchEquipId OBJECT-TYPE
SYNTAX Unsigned32 (7001..7100)
MAX-ACCESS read-only
STATUS current
DESCRIPTION
"Device ID of the DC load output branch. Value range: 007,001 to 007,100. The first digits indicate the device type and the last three digits indicate the SN of the device. "
 ::= { hwLoadBranchEntry 2 }

hwLoadBranchEquipName OBJECT-TYPE
SYNTAX OCTET STRING (SIZE (0..63))
MAX-ACCESS read-write
STATUS current
DESCRIPTION
"Device name of the DC load output branch, of the character string type, can be configured by users. Otherwise, the configured character can not be any other languages except English."
 ::= { hwLoadBranchEntry 3 }

hwLoadBranchCurrent OBJECT-TYPE
SYNTAX Unsigned32 (0..100000)
MAX-ACCESS read-only
STATUS current
DESCRIPTION
"DC load output branch current. It is an analog parameter collected by the load branch in real time. Value range: 0 to 10000, units: A, and the value is accurate to one decimal space (.1).  If the value is 2147483647(0x7FFFFFFF), it indicates that the value is invalid."
 ::= { hwLoadBranchEntry 4 }

hwLoadBranchPower OBJECT-TYPE
SYNTAX Unsigned32 (0..600000)
MAX-ACCESS read-only
STATUS current
DESCRIPTION
"DC load branch power. It is an analog parameter collected by the DC power in real time. Value range: 0 to 600000, units: W, and the value is an integer (.0).  If the value is 2147483647(0x7FFFFFFF), it indicates that the value is invalid."
 ::= { hwLoadBranchEntry 5 }

hwLoadBranchOperStatus OBJECT-TYPE
SYNTAX INTEGER
{
normal(1),
disconnect(2),
noresponse(3),
overload(4),
alarmResume(254),
other(255)
}
MAX-ACCESS read-only
STATUS current
DESCRIPTION
"State of the site load output branch. It is an enumeration type: 
  If the enumeration value is 1, it indicates that the site load output branch is in the normal state; 
  If the enumeration value is 2, it indicates that the load output branch disconnect;
 If the enumeration value is 3, it indicates that the site load output branch is in noresponse state; 
 If the enumeration value is 2, it indicates that the site load output branch is in the overload state; 
  If the enumeration value is 254, it indicates load output branch alarm resume; 
  If the enumeration value is 255, it indicates load output branch operation status unknown. "
 ::= { hwLoadBranchEntry 99 }

hwLoadBranchRowStatus OBJECT-TYPE
SYNTAX RowStatus
MAX-ACCESS read-create
STATUS current
DESCRIPTION
"RowStatus of loads output branch."
 ::= { hwLoadBranchEntry 100 }

hwLvdUnits OBJECT IDENTIFIER ::= { hwSiteMonitorMIBObjects 7 }

hwLvdsGroup OBJECT IDENTIFIER ::= { hwLvdUnits 1 }

hwLvdsGroupId OBJECT-TYPE
SYNTAX Unsigned32
MAX-ACCESS read-only
STATUS current
DESCRIPTION
"LVD unit group ID. It is the unique ID of the LVD unit group. The first digits indicate the device type. The last three digits indicate the device SN. If the last three digits are 000, it indicates a virtual device."
 ::= { hwLvdsGroup 1 }

hwLvdsGroupName OBJECT-TYPE
SYNTAX OCTET STRING (SIZE (0..63))
MAX-ACCESS read-write
STATUS current
DESCRIPTION
"Low-voltage power-off unit group name, of the character string type, can be configured by users.
Otherwise, the configured character can not be any other languages except English."
 ::= { hwLvdsGroup 2 }

hwLvdsTotalQuantity OBJECT-TYPE
SYNTAX Unsigned32 (0..100)
MAX-ACCESS read-only
STATUS current
DESCRIPTION
"Total quantity of power-off units. Value range: 0 to 100."
 ::= { hwLvdsGroup 3 }

hwLvdUnit OBJECT IDENTIFIER ::= { hwLvdUnits 2 }

hwLvdBranchTable OBJECT-TYPE
SYNTAX SEQUENCE OF HwLvdBranchEntry
MAX-ACCESS not-accessible
                                             STATUS current
                                             DESCRIPTION
"Power-off unit table. Use this table to get Lvd unit equipment ID and power-off unit equipment name, set power-off enable and power-off voltage, as well as control power-off unit disconnected. This table's index is hwLvdBranchIndex, which qualificated by hwLvdsQuantity, clone power-off unit table."
 ::= { hwLvdUnit 1 }

hwLvdBranchEntry OBJECT-TYPE
SYNTAX HwLvdBranchEntry
MAX-ACCESS not-accessible
                                             STATUS current
                                             DESCRIPTION
"Power-off unit table. Use this table to get Lvd unit equipment ID and power-off unit equipment name, set power-off enable and power-off voltage, as well as control power-off unit disconnected. This table's index is hwLvdBranchIndex, which qualificated by hwLvdsQuantity, clone power-off unit table."
INDEX { hwLvdBranchIndex }
 ::= { hwLvdBranchTable 1 }

HwLvdBranchEntry ::= SEQUENCE {
hwLvdBranchIndex
 Integer32,
hwLvdUnitEquipId
 Unsigned32,
hwLvdUnitEquipName
 OCTET STRING,
hwSetLvdEnable
 INTEGER,
hwSetLvdVoltage
 Integer32,
hwCtrlLvd
 INTEGER,
hwSetLvdMode
 INTEGER,
hwSetLvdReconnectedVoltage
 Integer32,
hwSetLvdDisconnectedTime
 Integer32,
hwSetLvdDisconnectedCapacity
 Integer32,
hwLvdBranchOperStatus
 INTEGER,
hwLvdBranchRowStatus
 RowStatus
}

hwLvdBranchIndex OBJECT-TYPE
SYNTAX Integer32 (1..100)
MAX-ACCESS read-only
STATUS current
DESCRIPTION
"Device table index of a power-off unit. Value range: 1 to 100. Lines of the device list are restricted by the total quantity of the power-off units (hwLvdsTotalQuantity). "
 ::= { hwLvdBranchEntry 1 }

hwLvdUnitEquipId OBJECT-TYPE
SYNTAX Unsigned32 (8001..8100)
MAX-ACCESS read-only
STATUS current
DESCRIPTION
"Device ID of a power-off unit. Value range: 8001 to 8100. The first digits indicate the device type and the last three digits indicate the device SN. "
 ::= { hwLvdBranchEntry 2 }

hwLvdUnitEquipName OBJECT-TYPE
SYNTAX OCTET STRING (SIZE (0..63))
MAX-ACCESS read-write
STATUS current
DESCRIPTION
"Device name of a power-off unit, of the character string type, is used to specify the low-voltage power-off unit. Users can configure it. Otherwise, the configured character can not be any other languages except English. "
 ::= { hwLvdBranchEntry 3 }

hwSetLvdEnable OBJECT-TYPE
SYNTAX INTEGER
{
enabled(1),
disabled(2)
}
MAX-ACCESS read-write
STATUS current
DESCRIPTION
"Control power-off unit enabling. It is an enumeration value, and users actively set it. 
  If the enumeration value is 1, it means to enable the power-off unit; 
  If the enumeration value is 2, it means to disable the power-off unit. 
  When the power-off unit control is not configured, the power-off unit is enabled by default."
 ::= { hwLvdBranchEntry 4 }

hwSetLvdVoltage OBJECT-TYPE
SYNTAX Integer32 (350..560)
MAX-ACCESS read-write
STATUS current
DESCRIPTION
"Low-voltage power-off voltage of a power-off unit can be configured by users. Its value range: 35 to 56, units: V, and the value is accurate to one decimal space (.1).  If the value is 2147483647(0x7FFFFFFF), it indicates that the value is invalid.
NOTE: There is linkage between hwSetLvdVoltage and hwSetLvdReconnectedVoltage"
 ::= { hwLvdBranchEntry 5 }

hwCtrlLvd OBJECT-TYPE
SYNTAX INTEGER
{
powerOff(1),
powerOn(2),
nullOper(255)
}
MAX-ACCESS read-write
STATUS current
DESCRIPTION
"Control of the power-off unit. It is an enumeration value, users control it manually. 
  If the NMS notifies the SNMP agent that the node is set to 1, it means to power off the power-off unit; 
  If the NMS notifies the SNMP agent that the node is set to 2, it means that the background controls the power-on of the LVD unit. 
NOTE: Only the system in manual mode, this parameter can be configured successfully.
"
 ::= { hwLvdBranchEntry 6 }

hwSetLvdMode OBJECT-TYPE
SYNTAX INTEGER
{
    byVoltage(1),
    byTime(2),
    byCapacity(3),
    unknown(255)
}
MAX-ACCESS read-write
STATUS current
DESCRIPTION
"Select the control mode of the power-off unit. It is an enumeration value, users can configure it manually. 
    If the NMS notifies the SNMP agent that the node is set to 1, it means to select the voltage power off mode; 
    If the NMS notifies the SNMP agent that the node is set to 2, it means to select the time power off mode;  
    If the NMS notifies the SNMP agent that the node is set to 3, it means to select the capacity power off mode;"
 ::= { hwLvdBranchEntry 7 }

hwSetLvdReconnectedVoltage OBJECT-TYPE
SYNTAX Integer32 (370..580)
MAX-ACCESS read-write
STATUS current
DESCRIPTION
"Low-voltage power-off recover of a power-off unit can be configured by users. Its value range: 37.0 to 58.0, unit: V, and the value is accurate to one decimal space (.1).  If the value is 2147483647(0x7FFFFFFF), it indicates that the value is invalid.
   The default value is 51.5
NOTE: There is linkage between hwSetLvdVoltage and hwSetLvdReconnectedVoltage"
 ::= { hwLvdBranchEntry 8 }

hwSetLvdDisconnectedTime OBJECT-TYPE
SYNTAX Integer32 (5..1000)
MAX-ACCESS read-write
STATUS current
DESCRIPTION
"Low-voltage power-off disconnected time, It can be configured by users, and its value is an integer (.0). 
    Here, if battery manual test is standard mode, value range defines between 5 to 1000, unit: minutes(m). If the value is 2147483647(0x7FFFFFFF), it indicates that the value is invalid.
NOTE: Only the lvd in time power off mode, this parameter can be configured successfully."
 ::= { hwLvdBranchEntry 9 }

hwSetLvdDisconnectedCapacity OBJECT-TYPE
SYNTAX Integer32 (0..1000)
MAX-ACCESS read-write
STATUS current
DESCRIPTION
"Power-off unit control the power off, when Remaining capacity percentage of the battery strings is below the calue. Value range: 0 to 100, unit: %, and the value is accurate to one decimal place (.1).  If the value is 2147483647(0x7FFFFFFF), it indicates that the value is invalid.
NOTE: Only the lvd in capacity power off mode, this parameter can be configured successfully."
 ::= { hwLvdBranchEntry 10 }

hwLvdBranchOperStatus OBJECT-TYPE
SYNTAX INTEGER
{
normal(1),
lowVoltOff(2),
backgroundOff(3),
localManualOff(4),
lowTempOff(5),
highTempOff(6),
timeOff(7),
capacityOff(8),
forceOff(9),
alarmResume(254),
other(255)
}
MAX-ACCESS read-only
STATUS current
DESCRIPTION
"State of the site LVD uint. It is an enumeration type: 
  If the enumeration value is 1, the site LVD uint is in the normal state;
  If the enumeration value is 2, the power-off uint disconnect for low voltage;  
  If the enumeration value is 3, the power-off uint disconnect bakeground;   
  If the enumeration value is 4, the power-off uint local disconnect manually;  
  If the enumeration value is 5, the power-off uint disconnect for under temperature; 
  If the enumeration value is 6, the power-off uint disconnect for over temperature; 
  If the enumeration value is 7, the ower-off uint disconnect for time;
If the enumeration value is 8, the power-off uint disconnect for capacity;
If the enumeration value is 9, the power-off uint disconnect for force;
  If the enumeration value is 254, the power-off uint alarm resume; 
  If the enumeration value is 255, it indicates LVD uint operation status unknown. "
 ::= { hwLvdBranchEntry 99 }

hwLvdBranchRowStatus OBJECT-TYPE
SYNTAX RowStatus
MAX-ACCESS read-create
STATUS current
DESCRIPTION
"RowStatus of lvd table."
 ::= { hwLvdBranchEntry 100 }

hwSiteEnvUnits OBJECT IDENTIFIER ::= { hwSiteMonitorMIBObjects 8 }

hwEnvUnitsGroup OBJECT IDENTIFIER ::= { hwSiteEnvUnits 1 }

hwEnvUnitsGroupId OBJECT-TYPE
SYNTAX Unsigned32
MAX-ACCESS read-only
STATUS current
DESCRIPTION
"Unit group ID of the site environment. It is the unique ID of the unit group on the site. The first digits indicate the device type. The last three digits indicate the device SN. If the last three digits are 000, it indicates a virtual device. "
 ::= { hwEnvUnitsGroup 1 }

hwEnvUnitsGroupName OBJECT-TYPE
SYNTAX OCTET STRING (SIZE (0..63))
MAX-ACCESS read-write
STATUS current
DESCRIPTION
"Unit group name of the site environment, of the character string type, can be configured by users.
Otherwise, the configured character can not be any other languages except English."
 ::= { hwEnvUnitsGroup 2 }

hwCtrlSmokeReset OBJECT-TYPE
SYNTAX INTEGER
{
normal(1),
reset(2),
nullOper(255)
}
MAX-ACCESS read-write
STATUS current
DESCRIPTION
"Smoke sensor reset. It manually controls clearance of the smoke sensor alarm, and this node is of the enumeration type. 
  If the enumeration value is 1, it indicates that the reset of the smoke sensor is not required. 
  If the enumeration value of the node is 2, it indicates that the background controls the reset of the smoke sensor. "
 ::= { hwEnvUnitsGroup 3 }

hwCtrlDoorReset OBJECT-TYPE
SYNTAX INTEGER
{
normal(1),
reset(2),
nullOper(255)
}
MAX-ACCESS read-write
STATUS current
DESCRIPTION
"Door actuator reset control. It manually controls clearance of the door actuator alarm. This node is of the enumeration type. 
  If the enumeration value is 1, it indicates that clearance of the door actuator is not required;
  If the enumeration value is 2, it indicates that the background controls clearance of the door actuator. "
 ::= { hwEnvUnitsGroup 4 }

hwCtrlBuzzerEnable OBJECT-TYPE
SYNTAX INTEGER
{
enable(1),
disable(2),
nullOper(255)
}
MAX-ACCESS read-write
STATUS current
DESCRIPTION
"Buzzer enabling. It manually controls the enabling of the buzzer alarm. This node is of the enumeration type. 
  When the enumeration value is 1, it means to enable the buzzer;
  When the enumeration value is 2, it means to disable the buzzer. "
 ::= { hwEnvUnitsGroup 5 }

hwEnvTempSensorsTotalQuantity OBJECT-TYPE
SYNTAX Unsigned32 (0..256)
MAX-ACCESS read-only
STATUS current
DESCRIPTION
"Quantity of the environment temperature sensors, and its value range: 0 to 256."
 ::= { hwEnvUnitsGroup 6 }

hwEnvHumiSensorsTotalQuantity OBJECT-TYPE
SYNTAX Unsigned32 (0..256)
MAX-ACCESS read-only
STATUS current
DESCRIPTION
"Quantity of the environment humidity sensors, and its value range: 0 to 256."
 ::= { hwEnvUnitsGroup 7 }

hwSpareDigitalsTotalQuantity OBJECT-TYPE
SYNTAX Unsigned32 (0..256)
MAX-ACCESS read-only
STATUS current
DESCRIPTION
"Quantity of the Spare digitals, and its value range: 0 to 256."
 ::= { hwEnvUnitsGroup 8 }

hwSpareDigitalsOutputQuantity OBJECT-TYPE
SYNTAX Unsigned32 (0..256)
MAX-ACCESS read-only
STATUS current
DESCRIPTION
"Quantity of the Spare digitals Output, and its value range: 0 to 256."
 ::= { hwEnvUnitsGroup 9 }

hwEnvSensor OBJECT IDENTIFIER ::= { hwSiteEnvUnits 2 }

hwEnvTempSensorTable OBJECT-TYPE
SYNTAX SEQUENCE OF HwEnvTempSensorEntry
MAX-ACCESS not-accessible
                                             STATUS current
                                             DESCRIPTION
"Site environment temperature table. Use this table to get environment temperature equipment ID, environment temperature equipment name, and environment temperature, set environment temperature upper limit, environment temperature lower limit, and environment temperature alarm enable. This table's index is hwEnvTempSensorIndex, which qualificated by hwEnvTempSensorsQuantity, clone site environment temperature table."
 ::= { hwEnvSensor 1 }

hwEnvTempSensorEntry OBJECT-TYPE
SYNTAX HwEnvTempSensorEntry
MAX-ACCESS not-accessible
                                             STATUS current
                                             DESCRIPTION
"Site environment temperature table. Use this table to get environment temperature equipment ID, environment temperature equipment name, and environment temperature, set environment temperature upper limit, environment temperature lower limit, and environment temperature alarm enable. This table's index is hwEnvTempSensorIndex, which qualificated by hwEnvTempSensorsQuantity, clone site environment temperature table."
INDEX { hwEnvTempSensorIndex }
 ::= { hwEnvTempSensorTable 1 }

HwEnvTempSensorEntry ::= SEQUENCE {
hwEnvTempSensorIndex
 Integer32,
hwEnvTempEquipId
 Unsigned32,
hwEnvTempEquipName
 OCTET STRING,
hwEnvTemperature
 Integer32,
hwSetEnvTempUpperLimit
 Integer32,
hwSetEnvTempLowerLimit
 Integer32,
hwSetEnvTempMeasureUpperLimit
 Integer32,
hwSetEnvTempMeasureLowerLimit
 Integer32,
hwSetEnvTempAlarmEnable
 INTEGER,
hwEnvTempSensorOperStatus
 INTEGER,
hwEnvTempSensorRowStatus
 RowStatus
}

hwEnvTempSensorIndex OBJECT-TYPE
SYNTAX Integer32 (1..256)
MAX-ACCESS read-only
STATUS current
DESCRIPTION
"Table index of the environment temperature sensors. Value range: 1 to 256. Lines of the device table are restricted by the quantity of environment temperature sensors (hwEnvTempSensorsTotalQuantity). "
 ::= { hwEnvTempSensorEntry 1 }

hwEnvTempEquipId OBJECT-TYPE
SYNTAX Unsigned32 (9001..9255)
MAX-ACCESS read-only
STATUS current
DESCRIPTION
"Environment temperature sensor ID. Value range: 009'001 to 009'255, in which the first digits indicate the device type and the last three digits indicate the device SN. "
 ::= { hwEnvTempSensorEntry 2 }

hwEnvTempEquipName OBJECT-TYPE
SYNTAX OCTET STRING (SIZE (0..63))
MAX-ACCESS read-write
STATUS current
DESCRIPTION
"Environment temperature sensor name, of the character string type,  is used to specify an environment temperature sensor. Users can configure it. Otherwise, the configured character can not be any other languages except English. "
 ::= { hwEnvTempSensorEntry 3 }

hwEnvTemperature OBJECT-TYPE
SYNTAX Integer32 ( -50..100)
MAX-ACCESS read-only
STATUS current
DESCRIPTION
"Environment temperature. It is an environment parameter collected in real time. Value range: -50 to +100, units: centigrade (°C), and the value is an integer (.0).  If the value is -1024, it indicates that the temperature sensor is not configured."
 ::= { hwEnvTempSensorEntry 4 }

hwSetEnvTempUpperLimit OBJECT-TYPE
SYNTAX Integer32 ( 25..80)
MAX-ACCESS read-write
STATUS current
DESCRIPTION
"Upper threshold of the environment temperature alarm, can be configured by users. Value range: 25 to 80, units: centigrade (°C), and the value is an integer (.0).  If the value is 2147483647(0x7FFFFFFF), it indicates that the value is invalid.
NOTE: There is linkage between hwSetEnvTempUpperLimit and hwSetEnvTempLowerLimit"
 ::= { hwEnvTempSensorEntry 5 }

hwSetEnvTempLowerLimit OBJECT-TYPE
SYNTAX Integer32 ( -20..20)
MAX-ACCESS read-write
STATUS current
DESCRIPTION
"Lower threshold of the environment temperature alarm, can be configured by users. Value range: -20 to 20, units: centigrade (°C), and the value is an integer (.0).  If the value is 2147483647(0x7FFFFFFF), it indicates that the value is invalid.
NOTE: There is linkage between hwSetEnvTempUpperLimit and hwSetEnvTempLowerLimit"
 ::= { hwEnvTempSensorEntry 6 }

hwSetEnvTempMeasureUpperLimit OBJECT-TYPE
SYNTAX Integer32 (0..100)
MAX-ACCESS read-write
STATUS current
DESCRIPTION
"Upper threshold of the environment temperature measurement, can be configured by users. Value range: 0 to 100, unit: centigrade (°C), and the value is an integer (.0).  If the value is 2147483647(0x7FFFFFFF), it indicates that the value is invalid."
 ::= { hwEnvTempSensorEntry 7 }

hwSetEnvTempMeasureLowerLimit OBJECT-TYPE
SYNTAX Integer32 ( -50..0)
MAX-ACCESS read-write
STATUS current
DESCRIPTION
"Lower threshold of the environment temperature measurement, can be configured by users. Value range: -50 to 0, unit: centigrade (°C), and the value is an integer (.0).  If the value is 2147483647(0x7FFFFFFF), it indicates that the value is invalid."
 ::= { hwEnvTempSensorEntry 8 }

hwSetEnvTempAlarmEnable OBJECT-TYPE
SYNTAX INTEGER
{
enable(1),
disable(2)
}
MAX-ACCESS read-write
STATUS current
DESCRIPTION
"Environment temperature alarm. It is an enumeration type:
  If the enumeration value is 1, enable the alarm of the environment temperature; 
  If the enumeration value is 2, disable the alarm of the environment temperature. "
 ::= { hwEnvTempSensorEntry 9 }

hwEnvTempSensorOperStatus OBJECT-TYPE
SYNTAX INTEGER
{
normal(1),
tempHigh(2),
tempLow(3),
notInslot(4),
alarmResume(254),
other(255)
}
MAX-ACCESS read-only
STATUS current
DESCRIPTION
"State of the site environment temperature sensor. It is an enumeration type: 
  If the enumeration value is 1, it indicates that the site environment temperature sensor is in the normal state; 
  If the enumeration value is 2, it indicates that the environment temperature sensor is over temperature; 
  If the enumeration value is 3, it indicates that the environment temperature sensor is under temperature; 
  If the enumeration value is 4, it indicates that the environment temperature sensor is not in slot;
  If the enumeration value is 254, it indicates that environment temperature alarm resume; 
  If the enumeration value is 255, it indicates environment temperature sensor operation status unknown. "
 ::= { hwEnvTempSensorEntry 99 }

hwEnvTempSensorRowStatus OBJECT-TYPE
SYNTAX RowStatus
MAX-ACCESS read-create
STATUS current
DESCRIPTION
"RowStatus of Environment temperature table."
 ::= { hwEnvTempSensorEntry 100 }

hwEnvHumiSensorTable OBJECT-TYPE
SYNTAX SEQUENCE OF HwEnvHumiSensorEntry
MAX-ACCESS not-accessible
                                             STATUS current
                                             DESCRIPTION
"Environment humidity table. Use this table to get environment humidity equipment ID , environment humidity equipment name, and environment humidity, set environment humidity upper limit, environment humidity lower limit, and environment humidity alarm enable. This table's index is hwEnvHumiSensorIndex, which qualificated by hwEnvHumiSensorIndex, clone site environment humidity table."
 ::= { hwEnvSensor 2 }

hwEnvHumiSensorEntry OBJECT-TYPE
SYNTAX HwEnvHumiSensorEntry
MAX-ACCESS not-accessible
                                             STATUS current
                                             DESCRIPTION
"Environment humidity table. Use this table to get environment humidity equipment ID , environment humidity equipment name, and environment humidity, set environment humidity upper limit, environment humidity lower limit, and environment humidity alarm enable. This table's index is hwEnvHumiSensorIndex, which qualificated by hwEnvHumiSensorIndex, clone site environment humidity table."
INDEX { hwEnvHumiSensorIndex }
 ::= { hwEnvHumiSensorTable 1 }

HwEnvHumiSensorEntry ::= SEQUENCE {
hwEnvHumiSensorIndex
 Integer32,
hwEnvHumiEquipId
 Unsigned32,
hwEnvHumiEquipName
 OCTET STRING,
hwEnvHumidity
 Integer32,
hwSetEnvHumidityUpperLimit
 Integer32,
hwSetEnvHumidityLowerLimit
 Integer32,
hwSetEnvHumidityMeasureUpperLimit
 Integer32,
hwSetEnvHumidityMeasureLowerLimit
 Integer32,
hwSetEnvHumiAlarmEnable
 INTEGER,
hwEnvHumiSensorOperStatus
 INTEGER,
hwEnvHumiSensorRowStatus
 RowStatus
}

hwEnvHumiSensorIndex OBJECT-TYPE
SYNTAX Integer32 (1..256)
MAX-ACCESS read-only
STATUS current
DESCRIPTION
"Table index of the environment humility sensors. Value range: 1 to 256. Lines of the device list are restricted by the quantity of environment humility sensors (hwEnvHumiSensorsTotalQuantity). "
 ::= { hwEnvHumiSensorEntry 1 }

hwEnvHumiEquipId OBJECT-TYPE
SYNTAX Unsigned32 (10001..10255)
MAX-ACCESS read-only
STATUS current
DESCRIPTION
"Environment humility sensor ID, can be configured by users. Value range: 010'001 to 010'255, in which the first digits indicate the device type and the last three digits indicate the device SN."
 ::= { hwEnvHumiSensorEntry 2 }

hwEnvHumiEquipName OBJECT-TYPE
SYNTAX OCTET STRING (SIZE (0..63))
MAX-ACCESS read-write
STATUS current
DESCRIPTION
"Environment humility sensor name, of the character string type, is used to specify an environment humility sensor. Users can configure it.Otherwise, the configured character can not be any other languages except English. "
 ::= { hwEnvHumiSensorEntry 3 }

hwEnvHumidity OBJECT-TYPE
SYNTAX Integer32 (0..100)
MAX-ACCESS read-only
STATUS current
DESCRIPTION
"Environment humility. It is an environment parameter collected in real time. Value range: 0 to 100, units: %RH, and the value is an integer (.0). If the value is 2147483647(0x7FFFFFFF), it indicates that the humidity sensor is not configured."
 ::= { hwEnvHumiSensorEntry 4 }

hwSetEnvHumidityUpperLimit OBJECT-TYPE
SYNTAX Integer32 (0..100)
MAX-ACCESS read-write
STATUS current
DESCRIPTION
"Upper threshold of the environment humility alarm, can be configured by users. Value range: 0 to 100, units: %RH, and the value is an integer (.0).  If the value is 2147483647(0x7FFFFFFF), it indicates that the value is invalid."
 ::= { hwEnvHumiSensorEntry 5 }

hwSetEnvHumidityLowerLimit OBJECT-TYPE
SYNTAX Integer32 (0..100)
MAX-ACCESS read-write
STATUS current
DESCRIPTION
"Lower threshold of the environment humility alarm, can be configured by users. Value range: 0 to 100, units: %RH, and the value is an integer (.0).  If the value is 2147483647(0x7FFFFFFF), it indicates that the value is invalid."
 ::= { hwEnvHumiSensorEntry 6 }

hwSetEnvHumidityMeasureUpperLimit OBJECT-TYPE
SYNTAX Integer32 (0..100)
MAX-ACCESS read-write
STATUS current
DESCRIPTION
"Upper threshold of the environment humility measurement, can be configured by users. Value range: 0 to 100, units: %RH, and the value is an integer (.0).  If the value is 2147483647(0x7FFFFFFF), it indicates that the value is invalid."
 ::= { hwEnvHumiSensorEntry 7 }

hwSetEnvHumidityMeasureLowerLimit OBJECT-TYPE
SYNTAX Integer32 (0..100)
MAX-ACCESS read-write
STATUS current
DESCRIPTION
"Lower threshold of the environment humility measurement, can be configured by users. Value range: 0 to 100, units: %RH, and the value is an integer (.0).  If the value is 2147483647(0x7FFFFFFF), it indicates that the value is invalid."
 ::= { hwEnvHumiSensorEntry 8 }

hwSetEnvHumiAlarmEnable OBJECT-TYPE
SYNTAX INTEGER
{
enable(1),
disable(2)
}
MAX-ACCESS read-write
STATUS current
DESCRIPTION
"Environment humility alarm. It is an enumeration type:
  If the enumeration value is 1, enable the alarm of the environment humility; 
  If the enumeration value is 2, disable the alarm of the environment humility. 
  The environment humility alarm is enabled by default. "
 ::= { hwEnvHumiSensorEntry 9 }

hwEnvHumiSensorOperStatus OBJECT-TYPE
SYNTAX INTEGER
{
normal(1),
humidityHigh(2),
humidityLow(3),
notInslot(4),
alarmResume(254),
other(255)
}
MAX-ACCESS read-only
STATUS current
DESCRIPTION
"State of the site environment humidity sensor. It is an enumeration type: 
  If the enumeration value is 1, it indicates that the site environment humidity sensor is in the normal state; 
  If the enumeration value is 2, it indicates that the environment humidity sensor is over humidity; 
  If the enumeration value is 3, it indicates that the environment humidity sensor is under humidity;
  If the enumeration value is 4, it indicates that the environment humidity sensor is not in slot;
  If the enumeration value is 254, it indicates that environment humidity alarm resume;   
  If the enumeration value is 255, it indicates environment humidity sensor operation status unknown.  "
 ::= { hwEnvHumiSensorEntry 99 }

hwEnvHumiSensorRowStatus OBJECT-TYPE
SYNTAX RowStatus
MAX-ACCESS read-create
STATUS current
DESCRIPTION
"RowStatus of Environment humidity table."
 ::= { hwEnvHumiSensorEntry 100 }

hwSpareDigitalTable OBJECT-TYPE
SYNTAX SEQUENCE OF HwSpareDigitalEntry
MAX-ACCESS not-accessible
                                             STATUS current
                                             DESCRIPTION
"Spare digital table. Use this table to get Spare digital equipment ID , Spare digital equipment name, and current Spare digital alarm tension, ae well as to set Spare digital alarm enable. This table's index is hwSpareDigitalIndex, which qualificated by hwSpareDigitalsTotalQuantity, clone switch input table."
 ::= { hwEnvSensor 3 }

hwSpareDigitalEntry OBJECT-TYPE
SYNTAX HwSpareDigitalEntry
MAX-ACCESS not-accessible
                                             STATUS current
                                             DESCRIPTION
"Spare digital table. Use this table to get Spare digital equipment ID , Spare digital equipment name, and current Spare digital alarm tension, ae well as to set Spare digital alarm enable. This table's index is hwSpareDigitalIndex, which qualificated by hwSpareDigitalsTotalQuantity, clone switch input table."
INDEX { hwSpareDigitalIndex }
 ::= { hwSpareDigitalTable 1 }

HwSpareDigitalEntry ::= SEQUENCE {
hwSpareDigitalIndex
 Integer32,
hwSpareDigitalEquipId
 Unsigned32,
hwSpareDigitalEquipName
 OCTET STRING,
hwSetSpareDigitalAlarmTension
 INTEGER,
hwSetSpareDigitalAlarmEnable
 INTEGER,
hwSpareDigitalOperStatus
 INTEGER,
hwSpareDigitalRowStatus
 RowStatus
}

hwSpareDigitalIndex OBJECT-TYPE
SYNTAX Integer32 (1..256)
MAX-ACCESS read-only
STATUS current
DESCRIPTION
"Spare digital table index, which value range: 1 to 256. Lines of the device list are restricted by the quantity of Spare digitals (hwSpareDigitalsTotalQuantity). "
 ::= { hwSpareDigitalEntry 1 }

hwSpareDigitalEquipId OBJECT-TYPE
SYNTAX Unsigned32 (11001..11255)
MAX-ACCESS read-only
STATUS current
DESCRIPTION
"Spare digital device ID. Value range: 011'001 to 011'255, in which the first digits indicate the device type and the last three digits indicate the device SN. "
 ::= { hwSpareDigitalEntry 2 }

hwSpareDigitalEquipName OBJECT-TYPE
SYNTAX OCTET STRING (SIZE (0..63))
MAX-ACCESS read-write
STATUS current
DESCRIPTION
"Spare digital name, of the character string type, is used to specify Spare digitals. Users can configure it. Otherwise, the configured character can not be any other languages except English. "
 ::= { hwSpareDigitalEntry 3 }

hwSetSpareDigitalAlarmTension OBJECT-TYPE
SYNTAX INTEGER
{
open(0),
close(1)
}
MAX-ACCESS read-write
STATUS current
DESCRIPTION
"Spare digital alarm state. It is an enumeration value.  
  If the value of the node is 0, it indicates a low-tension alarm;
  If the value of the node is 1, it indicates a high-tension alarm. "
 ::= { hwSpareDigitalEntry 4 }

hwSetSpareDigitalAlarmEnable OBJECT-TYPE
SYNTAX INTEGER
{
enable(1),
disable(2)
}
MAX-ACCESS read-write
STATUS current
DESCRIPTION
"Spare digital alarm enabling. It is an enumeration type: 
  If the enumeration value is 1, it means to enable the alarm; 
  If the enumeration value is 2, it means to disable the alarm. "
 ::= { hwSpareDigitalEntry 5 }

hwSpareDigitalOperStatus OBJECT-TYPE
SYNTAX INTEGER
{
normal(1),
alarm(2),
alarmResume(254),
other(255)
}
MAX-ACCESS read-only
STATUS current
DESCRIPTION
"State of the site Spare digital. It is an enumeration type: 
  If the enumeration value is 1, it indicates that the Spare digital operation state is normal; 
  If the enumeration value is 2, it indicates that a alarm occurs on the Spare digital;  
  If the enumeration value is 254, it indicates that spare digital alarm resume;  
  If the enumeration value is 255, it indicates Spare digital operation status unknown."
 ::= { hwSpareDigitalEntry 99 }

hwSpareDigitalRowStatus OBJECT-TYPE
SYNTAX RowStatus
MAX-ACCESS read-create
STATUS current
DESCRIPTION
"RowStatus of Spare digital device table."
 ::= { hwSpareDigitalEntry 100 }

hwSpareDigitalOutputTable OBJECT-TYPE
SYNTAX SEQUENCE OF HwSpareDigitalOutputEntry
MAX-ACCESS not-accessible
                                             STATUS current
                                             DESCRIPTION
"Spare digital table. Use this table to get Spare digital equipment ID , Spare digital equipment name, and current Spare digital alarm tension, ae well as to set Spare digital alarm enable. This table's index is hwSpareDigitalIndex, which qualificated by hwSpareDigitalsTotalQuantity, clone switch input table."
 ::= { hwEnvSensor 4 }

hwSpareDigitalOutputEntry OBJECT-TYPE
SYNTAX HwSpareDigitalOutputEntry
MAX-ACCESS not-accessible
                                             STATUS current
                                             DESCRIPTION
"Spare digital table. Use this table to get Spare digital equipment ID , Spare digital equipment name, and current Spare digital alarm tension, ae well as to set Spare digital alarm enable. This table's index is hwSpareDigitalIndex, which qualificated by hwSpareDigitalsTotalQuantity, clone switch input table."
INDEX { hwSpareDigitalOutputIndex }
 ::= { hwSpareDigitalOutputTable 1 }

HwSpareDigitalOutputEntry ::= SEQUENCE {
hwSpareDigitalOutputIndex
 Integer32,
hwSpareDigitalOutputEquipId
 Unsigned32,
hwSpareDigitalOutputEquipName
 OCTET STRING,
hwSetSpareDigitalOutputAlarmCondition
 INTEGER,
hwSetSpareDigitalOutputAction
 INTEGER,
hwSpareDigitalOutputOperStatus
 INTEGER,
hwSpareDigitalOutputRowStatus
 RowStatus
}

hwSpareDigitalOutputIndex OBJECT-TYPE
SYNTAX Integer32 (1..256)
MAX-ACCESS read-only
STATUS current
DESCRIPTION
"Spare digital table index, which value range: 1 to 256. Lines of the device list are restricted by the quantity of Spare digitals (hwSpareDigitalsTotalQuantity). "
 ::= { hwSpareDigitalOutputEntry 1 }

hwSpareDigitalOutputEquipId OBJECT-TYPE
SYNTAX Unsigned32 (11001..11255)
MAX-ACCESS read-only
STATUS current
DESCRIPTION
"Spare digital device ID. Value range: 011'001 to 011'255, in which the first digits indicate the device type and the last three digits indicate the device SN. "
 ::= { hwSpareDigitalOutputEntry 2 }

hwSpareDigitalOutputEquipName OBJECT-TYPE
SYNTAX OCTET STRING (SIZE (0..63))
MAX-ACCESS read-write
STATUS current
DESCRIPTION
"Spare digital name, of the character string type, is used to specify Spare digitals. Users can configure it. Otherwise, the configured character can not be any other languages except English. "
 ::= { hwSpareDigitalOutputEntry 3 }

hwSetSpareDigitalOutputAlarmCondition OBJECT-TYPE
SYNTAX INTEGER
{
open(1),
close(2)
}
MAX-ACCESS read-write
STATUS current
DESCRIPTION
"Spare digital alarm state. It is an enumeration value.  
  If the value of the node is 0, it indicates a low-tension alarm;
  If the value of the node is 1, it indicates a high-tension alarm. "
 ::= { hwSpareDigitalOutputEntry 4 }

hwSetSpareDigitalOutputAction OBJECT-TYPE
SYNTAX INTEGER
{
enable(1),
disable(2)
}
MAX-ACCESS read-write
STATUS current
DESCRIPTION
"Spare digital alarm enabling. It is an enumeration type: 
  If the enumeration value is 1, it means to enable the alarm; 
  If the enumeration value is 2, it means to disable the alarm. "
 ::= { hwSpareDigitalOutputEntry 5 }

hwSpareDigitalOutputOperStatus OBJECT-TYPE
SYNTAX INTEGER
{
open(1),
close(2),
alarmResume(254),
other(255)
}
MAX-ACCESS read-only
STATUS current
DESCRIPTION
"State of the site Spare digital. It is an enumeration type: 
  If the enumeration value is 1, it indicates that the Spare digital operation state is normal; 
  If the enumeration value is 2, it indicates that a alarm occurs on the Spare digital;  
  If the enumeration value is 254, it indicates that spare digital alarm resume;  
  If the enumeration value is 255, it indicates Spare digital operation status unknown."
 ::= { hwSpareDigitalOutputEntry 99 }

hwSpareDigitalOutputRowStatus OBJECT-TYPE
SYNTAX RowStatus
MAX-ACCESS read-create
STATUS current
DESCRIPTION
"RowStatus of Spare digital device table."
 ::= { hwSpareDigitalOutputEntry 100 }

hwSiteInverters OBJECT IDENTIFIER ::= { hwSiteMonitorMIBObjects 9 }

hwInverterGroup OBJECT IDENTIFIER ::= { hwSiteInverters 1 }

hwInverterGroupId OBJECT-TYPE
SYNTAX Unsigned32 (18001..18255)
MAX-ACCESS read-only
STATUS current
DESCRIPTION
"Inverter unit group ID.Value range: 018'001 to 018'255, in which the first digits indicate the device type and the last three digits indicate the device SN. "
 ::= { hwInverterGroup 1 }

hwInverterGroupName OBJECT-TYPE
SYNTAX Unsigned32
MAX-ACCESS read-write
STATUS current
DESCRIPTION
"Inverter unit group name, of the character string type, can be configured by users.
Otherwise, the configured character can not be any other languages except English."
 ::= { hwInverterGroup 2 }

hwInverterQuantity OBJECT-TYPE
SYNTAX Unsigned32
MAX-ACCESS read-only
STATUS current
DESCRIPTION
"Total site intelligent Inverters. "
 ::= { hwInverterGroup 3 }

hwInverter OBJECT IDENTIFIER ::= { hwSiteInverters 2 }

hwInverterTable OBJECT-TYPE
SYNTAX SEQUENCE OF HwInverterEntry
MAX-ACCESS not-accessible
                                             STATUS current
                                             DESCRIPTION
"/"
 ::= { hwInverter 1 }

hwInverterEntry OBJECT-TYPE
SYNTAX HwInverterEntry
MAX-ACCESS not-accessible
                                             STATUS current
                                             DESCRIPTION
"/"
INDEX { hwInverterIndex }
 ::= { hwInverterTable 1 }

HwInverterEntry ::= SEQUENCE {
hwInverterIndex
 Unsigned32,
hwInverterEquipId
 Unsigned32,
hwInverterEquipName
 OCTET STRING,
hwInverterAcOutputVolt
 Unsigned32,
hwInverterAcOutputCurr
 Unsigned32,
hwInverterAcOutputFreq
 Unsigned32,
hwInverterAcOutputW
 Unsigned32,
hwInverterAcOutputVA
 Unsigned32,
hwInverterAcInputVolt
 Unsigned32,
hwInverterAcInputCurr
 Unsigned32,
hwInverterAcInputFreq
 Unsigned32,
hwInverterAcInputW
 Unsigned32,
hwInverterAcInputVA
 Unsigned32,
hwInverterDcInputVolt
 Unsigned32,
hwInverterDcInputCurr
 Unsigned32,
hwInverterDcInputPower
 Unsigned32,
hwInverterRevision
 Unsigned32,
hwInverterPhaseNum
 Unsigned32,
hwInverterAcGroupNum
 Unsigned32,
hwInverterDcGroupNum
 Unsigned32,
hwInverterMajorAlarmNum
 Unsigned32,
hwInverterMinorAlarmNum
 Unsigned32,
hwInverterT2SSerialNum
 Unsigned32,
hwInverterModuleTemp
 Unsigned32,
hwInverterOperStatus
 INTEGER,
hwInverterRowStatus
 RowStatus
}

hwInverterIndex OBJECT-TYPE
SYNTAX Unsigned32 (1..256)
MAX-ACCESS read-only
STATUS current
DESCRIPTION
"Inverter table index,which value range:1 to 10.Lines of the device list are restricted by the quantity of Inverter."
 ::= { hwInverterEntry 1 }

hwInverterEquipId OBJECT-TYPE
SYNTAX Unsigned32 (18001..18255)
MAX-ACCESS read-only
STATUS current
DESCRIPTION
"Inverter device ID. Value range: 018'001 to 018'255, in which the first digits indicate the device type and the last three digits indicate the device SN. "
 ::= { hwInverterEntry 2 }

hwInverterEquipName OBJECT-TYPE
SYNTAX OCTET STRING (SIZE (0..63))
MAX-ACCESS read-only
STATUS current
DESCRIPTION
"Inverter name, of the character string type, is used to specify Inverters. Users can configure it.
Otherwise, the configured character can not be any other languages except English. "
 ::= { hwInverterEntry 3 }

hwInverterAcOutputVolt OBJECT-TYPE
SYNTAX Unsigned32 (0..100000)
MAX-ACCESS read-only
STATUS current
DESCRIPTION
"Inverter AC Output voltage, Value range: 0.0 to 100000.0.Unit: V.and the value is accurate to one decimal space (.1).If the value is 2147483647(0x7FFFFFFF), it indicates that the value is invalid."
 ::= { hwInverterEntry 4 }

hwInverterAcOutputCurr OBJECT-TYPE
SYNTAX Unsigned32 (0..100000)
MAX-ACCESS read-only
STATUS current
DESCRIPTION
"Inverter AC Output current, Value range: 0.0 to 100000.0.Unit: A.and the value is accurate to one decimal space (.1).If the value is 2147483647(0x7FFFFFFF), it indicates that the value is invalid."
 ::= { hwInverterEntry 5 }

hwInverterAcOutputFreq OBJECT-TYPE
SYNTAX Unsigned32 (0..100000)
MAX-ACCESS read-only
STATUS current
DESCRIPTION
"Inverter AC Output frequency, Value range: 0.0 to 100000.0.Unit: Hz.and the value is accurate to one decimal space (.1).If the value is 2147483647(0x7FFFFFFF), it indicates that the value is invalid."
 ::= { hwInverterEntry 6 }

hwInverterAcOutputW OBJECT-TYPE
SYNTAX Unsigned32 (0..100000)
MAX-ACCESS read-only
STATUS current
DESCRIPTION
"Inverter AC Output power, Value range: 0.0 to 100000.0.Unit: W.and the value is accurate to one decimal space (.1).If the value is 2147483647(0x7FFFFFFF), it indicates that the value is invalid."
 ::= { hwInverterEntry 7 }

hwInverterAcOutputVA OBJECT-TYPE
SYNTAX Unsigned32 (0..100000)
MAX-ACCESS read-only
STATUS current
DESCRIPTION
"Inverter AC Output power, Value range: 0.0 to 100000.0.Unit: VA.and the value is accurate to one decimal space (.1).If the value is 2147483647(0x7FFFFFFF), it indicates that the value is invalid."
 ::= { hwInverterEntry 8 }

hwInverterAcInputVolt OBJECT-TYPE
SYNTAX Unsigned32 (0..100000)
MAX-ACCESS read-only
STATUS current
DESCRIPTION
"Inverter AC Input voltage, Value range: 0.0 to 100000.0.Unit: V.and the value is accurate to one decimal space (.1).If the value is 2147483647(0x7FFFFFFF), it indicates that the value is invalid."
 ::= { hwInverterEntry 9 }

hwInverterAcInputCurr OBJECT-TYPE
SYNTAX Unsigned32 (0..100000)
MAX-ACCESS read-only
STATUS current
DESCRIPTION
"Inverter AC Input current, Value range: 0.0 to 100000.0.Unit: A.and the value is accurate to one decimal space (.1). If the value is 2147483647(0x7FFFFFFF), it indicates that the value is invalid."
 ::= { hwInverterEntry 10 }

hwInverterAcInputFreq OBJECT-TYPE
SYNTAX Unsigned32 (0..100000)
MAX-ACCESS read-only
STATUS current
DESCRIPTION
"Inverter AC Input frequency, Value range: 0.0 to 100000.0.Unit: Hz.and the value is accurate to one decimal space (.1). If the value is 2147483647(0x7FFFFFFF), it indicates that the value is invalid."
 ::= { hwInverterEntry 11 }

hwInverterAcInputW OBJECT-TYPE
SYNTAX Unsigned32 (0..100000)
MAX-ACCESS read-only
STATUS current
DESCRIPTION
"Inverter AC Input power, Value range: 0.0 to 100000.0.Unit: W.and the value is accurate to one decimal space (.1).If the value is 2147483647(0x7FFFFFFF), it indicates that the value is invalid."
 ::= { hwInverterEntry 12 }

hwInverterAcInputVA OBJECT-TYPE
SYNTAX Unsigned32 (0..100000)
MAX-ACCESS read-only
STATUS current
DESCRIPTION
"Inverter AC Input power, Value range: 0.0 to 100000.0.Unit: VA.and the value is accurate to one decimal space (.1). If the value is 2147483647(0x7FFFFFFF), it indicates that the value is invalid."
 ::= { hwInverterEntry 13 }

hwInverterDcInputVolt OBJECT-TYPE
SYNTAX Unsigned32 (0..100000)
MAX-ACCESS read-only
STATUS current
DESCRIPTION
"Inverter DC Input voltage, Value range: 0.0 to 100000.0.Unit: V.and the value is accurate to one decimal space (.1). If the value is 2147483647(0x7FFFFFFF), it indicates that the value is invalid."
 ::= { hwInverterEntry 14 }

hwInverterDcInputCurr OBJECT-TYPE
SYNTAX Unsigned32 (0..100000)
MAX-ACCESS read-only
STATUS current
DESCRIPTION
"Inverter DC Input current, Value range: 0.0 to 100000.0.Unit: A.and the value is accurate to one decimal space (.1). If the value is 2147483647(0x7FFFFFFF), it indicates that the value is invalid."
 ::= { hwInverterEntry 15 }

hwInverterDcInputPower OBJECT-TYPE
SYNTAX Unsigned32 (0..100000)
MAX-ACCESS read-only
STATUS current
DESCRIPTION
"Inverter DC Input power, Value range: 0.0 to 100000.0.Unit: W.and the value is accurate to one decimal space (.1). If the value is 2147483647(0x7FFFFFFF), it indicates that the value is invalid."
 ::= { hwInverterEntry 16 }

hwInverterRevision OBJECT-TYPE
SYNTAX Unsigned32
MAX-ACCESS read-only
STATUS current
DESCRIPTION
"Inverter software version number."
 ::= { hwInverterEntry 17 }

hwInverterPhaseNum OBJECT-TYPE
SYNTAX Unsigned32 (0..10000)
MAX-ACCESS read-only
STATUS current
DESCRIPTION
"Inverter Number of the phase module, Value range: 0 to 10000. If the value is 2147483647(0x7FFFFFFF), it indicates that the value is invalid."
 ::= { hwInverterEntry 18 }

hwInverterAcGroupNum OBJECT-TYPE
SYNTAX Unsigned32 (0..10000)
MAX-ACCESS read-only
STATUS current
DESCRIPTION
"Inverter Number of AC group, Value range: 0 to 10000. If the value is 2147483647(0x7FFFFFFF), it indicates that the value is invalid."
 ::= { hwInverterEntry 19 }

hwInverterDcGroupNum OBJECT-TYPE
SYNTAX Unsigned32 (0..10000)
MAX-ACCESS read-only
STATUS current
DESCRIPTION
"Inverter Number of DC group, Value range: 0 to 10000. If the value is 2147483647(0x7FFFFFFF), it indicates that the value is invalid."
 ::= { hwInverterEntry 20 }

hwInverterMajorAlarmNum OBJECT-TYPE
SYNTAX Unsigned32 (0..10000)
MAX-ACCESS read-only
STATUS current
DESCRIPTION
"Inverter Number of Major alarm, Value range: 0 to 10000. If the value is 2147483647(0x7FFFFFFF), it indicates that the value is invalid."
 ::= { hwInverterEntry 21 }

hwInverterMinorAlarmNum OBJECT-TYPE
SYNTAX Unsigned32 (0..10000)
MAX-ACCESS read-only
STATUS current
DESCRIPTION
"Inverter Number of Minor alarm, Value range: 0 to 10000. If the value is 2147483647(0x7FFFFFFF), it indicates that the value is invalid."
 ::= { hwInverterEntry 22 }

hwInverterT2SSerialNum OBJECT-TYPE
SYNTAX Unsigned32 (0..4294967295)
MAX-ACCESS read-only
STATUS current
DESCRIPTION
"Inverter T2S serial number, Value range: 0 to 4294967295."
 ::= { hwInverterEntry 23 }

hwInverterModuleTemp OBJECT-TYPE
SYNTAX Unsigned32 (0..300)
MAX-ACCESS read-only
STATUS current
DESCRIPTION
"Inverter module Temperature,Value range: 0 to 300.Unit: deg.and the value is accurate to one decimal space (.1). If the value is 2147483647(0x7FFFFFFF), it indicates that the value is invalid."
 ::= { hwInverterEntry 24 }

hwInverterOperStatus OBJECT-TYPE
SYNTAX INTEGER
{
normal (1),
alarm (2),
alarmResume (254),
unknow (255)
}
MAX-ACCESS read-only
STATUS current
DESCRIPTION
"State of the Inverter. It is an enumeration type: 
If the enumeration value is 1, it indicates that the Inverter is in the normal state;
If the enumeration value is 2, it indicates that the Inverter is in the alarm state;  
If the enumeration value is 254, it indicates that the Inverter is in the resume state;   
If the enumeration value is 255, it indicates Inverter operation status unknown. "
 ::= { hwInverterEntry 99 }

hwInverterRowStatus OBJECT-TYPE
SYNTAX RowStatus
MAX-ACCESS read-only
STATUS current
DESCRIPTION
"RowStatus of Inverter table."
 ::= { hwInverterEntry 100 }

hwSiteCoolingDevices OBJECT IDENTIFIER ::= { hwSiteMonitorMIBObjects 10 }

hwCoolingDevicesGroup OBJECT IDENTIFIER ::= { hwSiteCoolingDevices 1 }

hwCoolingDevicesEquipId OBJECT-TYPE
SYNTAX Integer32 (19001..19255)
MAX-ACCESS read-only
STATUS current
DESCRIPTION
"CoolingDevices unit group ID. Value range: 019'001 to 019'255, in which the first digits indicate the device type and the last three digits indicate the device SN. "
 ::= { hwCoolingDevicesGroup 1 }

hwCoolingDevicesEquipName OBJECT-TYPE
SYNTAX OCTET STRING (SIZE (0..63))
MAX-ACCESS read-write
STATUS current
DESCRIPTION
"CoolingDevices unit group name, of the character string type, can be configured by users.
Otherwise, the configured character can not be any other languages except English."
 ::= { hwCoolingDevicesGroup 2 }

hwCoolingDevicesMode OBJECT-TYPE
SYNTAX INTEGER
{
fanOnly (1),
acOnly (2),
smartMode (3),
other (4)
}
MAX-ACCESS read-write
STATUS current
DESCRIPTION
"State of the CoolingDevices TC mode. It is an enumeration type: 
If the enumeration value is 1, it indicates that the CoolingDeviecs is in fanOnly state;
If the enumeration value is 2, it indicates that the CoolingDeviecs is in acOnly state;
If the enumeration value is 3, it indicates that the CoolingDeviecs is in smartMode state;
If the enumeration value is 255, it indicates Inverter operation status unknown. "
 ::= { hwCoolingDevicesGroup 3 }

hwCoolingDevicesHighTempAlarmTres OBJECT-TYPE
SYNTAX Integer32 (25..80)
MAX-ACCESS read-write
STATUS current
DESCRIPTION
"CoolingDevices high temp alarm tres, Value range: 25 to 80 Unit: degC.and the value is accurate to one decimal space (.0).  If the value is 2147483647(0x7FFFFFFF), it indicates that the value is invalid."
 ::= { hwCoolingDevicesGroup 4 }

hwCoolingDevicesHighTempAlarmClearTres OBJECT-TYPE
SYNTAX Integer32 (25..80)
MAX-ACCESS read-write
STATUS current
DESCRIPTION
"CoolingDevices high temp alarm clear tres, Value range: 25 to 80 Unit: degC.and the value is accurate to one decimal space (.0).  If the value is 2147483647(0x7FFFFFFF), it indicates that the value is invalid."
 ::= { hwCoolingDevicesGroup 5 }

hwCoolingDevicesExpelHidry OBJECT-TYPE
SYNTAX INTEGER
{
no (1),
yes (2)
}
MAX-ACCESS read-write
STATUS current
DESCRIPTION
"State of the CoolingDevices expel hidry. It is an enumeration type: 
If the enumeration value is 1, it indicates that the CoolingDeviecs is in no state;
If the enumeration value is 2, it indicates that the CoolingDeviecs is in yes state;
"
 ::= { hwCoolingDevicesGroup 6 }

hwCoolingDevicesEquip OBJECT IDENTIFIER ::= { hwSiteCoolingDevices 2 }

hwFanTable OBJECT-TYPE
SYNTAX SEQUENCE OF HwFanEntry
MAX-ACCESS not-accessible
                                             STATUS current
                                             DESCRIPTION
"/"
 ::= { hwCoolingDevicesEquip 1 }

hwFanEntry OBJECT-TYPE
SYNTAX HwFanEntry
MAX-ACCESS not-accessible
                                             STATUS current
                                             DESCRIPTION
"/"
INDEX { hwFanIndex }
 ::= { hwFanTable 1 }

HwFanEntry ::= SEQUENCE {
hwFanIndex
 Unsigned32,
hwFanEquipId
 Unsigned32,
hwFanEquipName
 OCTET STRING,
hwFanCtrlMode
 INTEGER,
hwFan1Status
 INTEGER,
hwFan2Status
 INTEGER,
hwFan3Status
 INTEGER,
hwFan4Status
 INTEGER,
hwFan1Speed
 Integer32,
hwFan2Speed
 Integer32,
hwFan3Speed
 Integer32,
hwFan4Speed
 Integer32,
hwFanOperStatus
 INTEGER,
hwFanRowStatus
 RowStatus
}

hwFanIndex OBJECT-TYPE
SYNTAX Unsigned32 (1..256)
MAX-ACCESS read-only
STATUS current
DESCRIPTION
"Fan table index,which value range: 1 to 256.Lines of the device list are restricted by the quantity of Fan."
 ::= { hwFanEntry 1 }

hwFanEquipId OBJECT-TYPE
SYNTAX Unsigned32 (20001..20255)
MAX-ACCESS read-only
STATUS current
DESCRIPTION
"Fan device ID. Value range: 020'001 to 020'255, in which the first digits indicate the device type and the last three digits indicate the device SN. "
 ::= { hwFanEntry 2 }

hwFanEquipName OBJECT-TYPE
SYNTAX OCTET STRING (SIZE (0..63))
MAX-ACCESS read-only
STATUS current
DESCRIPTION
"Fan name, of the character string type, is used to specify Fans. Users can configure it.
Otherwise, the configured character can not be any other languages except English. "
 ::= { hwFanEntry 3 }

hwFanCtrlMode OBJECT-TYPE
SYNTAX INTEGER
{
autoControl (1),
manualControl (2),
other (3)
}
MAX-ACCESS read-write
STATUS current
DESCRIPTION
"State of the Fan ctrl mode. It is an enumeration type: 
If the enumeration value is 1, it indicates that the fan is in autoControl state;
If the enumeration value is 2, it indicates that the fan is in manualControl state;
If the enumeration value is 3, it indicates that the fan is in other state;"
 ::= { hwFanEntry 4 }

hwFan1Status OBJECT-TYPE
SYNTAX INTEGER
{
normal (1),
fault (2),
inexistent (3),
other (4)
}
MAX-ACCESS read-only
STATUS current
DESCRIPTION
"State of the Fan1 status. It is an enumeration type: 
If the enumeration value is 1, it indicates that the fan is in normal state;
If the enumeration value is 2, it indicates that the fan is in fault state;
If the enumeration value is 3, it indicates that the fan is in inexistent state;
If the enumeration value is 4, it indicates that the fan is in other state;"
 ::= { hwFanEntry 5 }

hwFan2Status OBJECT-TYPE
SYNTAX INTEGER
{
normal (1),
fault (2),
inexistent (3),
other (4)
}
MAX-ACCESS read-only
STATUS current
DESCRIPTION
"State of the Fan2 status. It is an enumeration type: 
If the enumeration value is 1, it indicates that the fan is in normal state;
If the enumeration value is 3, it indicates that the fan is in fault state;
If the enumeration value i, it indicates that the fan is in inexistent state;
If the enumeration value is 4, it indicates that the fan is in inexistent stat"
 ::= { hwFanEntry 6 }

hwFan3Status OBJECT-TYPE
SYNTAX INTEGER
{
normal (1),
fault (2),
inexistent (3),
other (4)
}
MAX-ACCESS read-only
STATUS current
DESCRIPTION
"State of the Fan3 status. It is an enumeration type: 
If the enumeration value is 1, it indicates that the fan is in normal state;
If the enumeration value is 4, it indicates that the fan is in fault state;
If the enumeration value i, it indicates that the fan is in inexistent state;
If the enumeration value is 4, it indicates that the fan is in inexistent stat"
 ::= { hwFanEntry 7 }

hwFan4Status OBJECT-TYPE
SYNTAX INTEGER
{
normal (1),
fault (2),
inexistent (3),
other (4)
}
MAX-ACCESS read-only
STATUS current
DESCRIPTION
"State of the Fan4 status. It is an enumeration type: 
If the enumeration value is 1, it indicates that the fan is in normal state;
If the enumeration value is 5, it indicates that the fan is in fault state;
If the enumeration value i, it indicates that the fan is in inexistent state;
If the enumeration value is 4, it indicates that the fan is in inexistent stat"
 ::= { hwFanEntry 8 }

hwFan1Speed OBJECT-TYPE
SYNTAX Integer32 (0..10000)
MAX-ACCESS read-only
STATUS current
DESCRIPTION
"Fan1 speed, Value range: 0 to 10000.Unit: rpm.the value is an integer (.0). If the value is 2147483647(0x7FFFFFFF), it indicates that the value is invalid."
 ::= { hwFanEntry 9 }

hwFan2Speed OBJECT-TYPE
SYNTAX Integer32 (0..10000)
MAX-ACCESS read-only
STATUS current
DESCRIPTION
"Fan2 speed, Value range: 0 to 10000.Unit: rpm.the value is an integer (.0). If the value is 2147483647(0x7FFFFFFF), it indicates that the value is invalid."
 ::= { hwFanEntry 10 }

hwFan3Speed OBJECT-TYPE
SYNTAX Integer32 (0..10000)
MAX-ACCESS read-only
STATUS current
DESCRIPTION
"Fan3 speed, Value range: 0 to 10000.Unit: rpm.the value is an integer (.0). If the value is 2147483647(0x7FFFFFFF), it indicates that the value is invalid."
 ::= { hwFanEntry 11 }

hwFan4Speed OBJECT-TYPE
SYNTAX Integer32 (0..10000)
MAX-ACCESS read-only
STATUS current
DESCRIPTION
"Fan4 speed, Value range: 0 to 10000.Unit: rpm.the value is an integer (.0). If the value is 2147483647(0x7FFFFFFF), it indicates that the value is invalid."
 ::= { hwFanEntry 12 }

hwFanOperStatus OBJECT-TYPE
SYNTAX INTEGER
{
normal (1),
fault (2),
alarmResume(254),
unknow(255)
}
MAX-ACCESS read-only
STATUS current
DESCRIPTION
"State of the fan. It is an enumeration type: 
If the enumeration value is 1, it indicates that the Inverter is in the normal state;
If the enumeration value is 2, it indicates that the Inverter is in the fault state;  
If the enumeration value is 254, it indicates that the Inverter is in the resume state;   
If the enumeration value is 255, it indicates Inverter operation status unknown. "
 ::= { hwFanEntry 99 }

hwFanRowStatus OBJECT-TYPE
SYNTAX RowStatus
MAX-ACCESS read-create
STATUS current
DESCRIPTION
"RowStatus fo fan table."
 ::= { hwFanEntry 100 }

hwDcAirConditionTable OBJECT-TYPE
SYNTAX SEQUENCE OF HwDcAirConditionEntry
MAX-ACCESS not-accessible
                                             STATUS current
                                             DESCRIPTION
""
 ::= { hwCoolingDevicesEquip 2 }

hwDcAirConditionEntry OBJECT-TYPE
SYNTAX HwDcAirConditionEntry
MAX-ACCESS not-accessible
                                             STATUS current
                                             DESCRIPTION
""
INDEX { hwDcAirIndex }
 ::= { hwDcAirConditionTable 1 }

HwDcAirConditionEntry ::= SEQUENCE {
hwDcAirIndex
 Unsigned32,
hwDcAirEquipId
 Unsigned32,
hwDcAirEquipName
 OCTET STRING,
hwDcAirCtrlMode
 INTEGER,
hwDcAirCtrlOnOff
 INTEGER,
hwDcAirRunStatus
 INTEGER,
hwDcAirCompressorRunStatus
 INTEGER,
hwDcAirInnrFanSpeed
 Integer32,
hwDcAirOuterFanSpeed
 Integer32,
hwDcAirCompressorRunTime
 Integer32,
hwDcAirRunTime
 Integer32,
hwDcAirDCInputVoltage
 Integer32,
hwDcAirEnterChannelTemp
 Integer32,
hwDcAirPowerOnTempPoint
 Integer32,
hwDcAirPowerOffTempPoint
 Integer32,
hwDcAirPowerOnBatteryTempPoint
 Integer32,
hwAcOffEnergySaving
 INTEGER,
hwDcAirPowerOnAcOffPoint
 Integer32,
hwDcAirPowerOffAcOffPoint
 Integer32,
hwDcAirCompressorStartTemp
 Integer32,
hwDcAirOperStatus
 INTEGER,
hwDcAirRowStatus
 RowStatus
}

hwDcAirIndex OBJECT-TYPE
SYNTAX Unsigned32 (1..256)
MAX-ACCESS read-only
STATUS current
DESCRIPTION
"Dc aircondition table index,which value range: 1 to 256.Lines of the device list are restricted by the quantity of Fan."
 ::= { hwDcAirConditionEntry 1 }

hwDcAirEquipId OBJECT-TYPE
SYNTAX Unsigned32 (21001..21255)
MAX-ACCESS read-only
STATUS current
DESCRIPTION
"Dc aircondition device ID. Value range: 021'001 to 021'255, in which the first digits indicate the device type and the last three digits indicate the device SN. "
 ::= { hwDcAirConditionEntry 2 }

hwDcAirEquipName OBJECT-TYPE
SYNTAX OCTET STRING (SIZE (0..63))
MAX-ACCESS read-only
STATUS current
DESCRIPTION
"Dc aircondition name, of the character string type, is used to specify Fans. Users can configure it.
Otherwise, the configured character can not be any other languages except English. "
 ::= { hwDcAirConditionEntry 3 }

hwDcAirCtrlMode OBJECT-TYPE
SYNTAX INTEGER
{
autoControl (1),
manualControl (2),
other (3)
}
MAX-ACCESS read-write
STATUS current
DESCRIPTION
"State of the Dc aircondition ctrl mode. It is an enumeration type: 
If the enumeration value is 1, it indicates that the Dc aircondition is in autoControl state;
If the enumeration value is 2, it indicates that the Dc aircondition is in manualControl state;
If the enumeration value is 3, it indicates that the Dc aircondition is in other state;"
 ::= { hwDcAirConditionEntry 4 }

hwDcAirCtrlOnOff OBJECT-TYPE
SYNTAX INTEGER
{
on (1),
off (2)
}
MAX-ACCESS read-write
STATUS current
DESCRIPTION
"State of the Dc aircondition control on or off. It is an enumeration type: 
If the enumeration value is 1, it indicates that the Dc aircondition is in on state;
If the enumeration value is 2, it indicates that the Dc aircondition is in off state;"
 ::= { hwDcAirConditionEntry 5 }

hwDcAirRunStatus OBJECT-TYPE
SYNTAX INTEGER
{
standby (1),
run (2),
fault (3),
other (4)
}
MAX-ACCESS read-only
STATUS current
DESCRIPTION
"State of the Dc aircondition run status. It is an enumeration type: 
If the enumeration value is 1, it indicates that the Dc aircondition is in standby state;
If the enumeration value is 2, it indicates that the Dc aircondition is in run state;
If the enumeration value is 3, it indicates that the Dc aircondition is in fault state;"
 ::= { hwDcAirConditionEntry 6 }

hwDcAirCompressorRunStatus OBJECT-TYPE
SYNTAX INTEGER
{
standby (1),
run (2),
fault (3),
other (4)
}
MAX-ACCESS read-only
STATUS current
DESCRIPTION
"State of the Dc air compressor run status. It is an enumeration type: 
If the enumeration value is 1, it indicates that the Dc aircondition is in standby state;
If the enumeration value is 2, it indicates that the Dc aircondition is in run state;
If the enumeration value is 3, it indicates that the Dc aircondition is in fault state;"
 ::= { hwDcAirConditionEntry 7 }

hwDcAirInnrFanSpeed OBJECT-TYPE
SYNTAX Integer32 (0..60000)
MAX-ACCESS read-only
STATUS current
DESCRIPTION
"Dc aircondition innr speed, Value range: 0 to 60000.Unit: rpm,the value is an integer (.0). If the value is 2147483647(0x7FFFFFFF), it indicates that the value is invalid."
 ::= { hwDcAirConditionEntry 8 }

hwDcAirOuterFanSpeed OBJECT-TYPE
SYNTAX Integer32 (0..60000)
MAX-ACCESS read-only
STATUS current
DESCRIPTION
"Dc aircondition outer speed, Value range: 0.0 to 60000.0.Unit: rpm,the value is an integer (.0). If the value is 2147483647(0x7FFFFFFF), it indicates that the value is invalid."
 ::= { hwDcAirConditionEntry 9 }

hwDcAirCompressorRunTime OBJECT-TYPE
SYNTAX Integer32 (0..175200)
MAX-ACCESS read-only
STATUS current
DESCRIPTION
"Dc aircondition compressor run time, Value range: 0 to 175200.Unit: rpm,the value is an integer (.0). If the value is 2147483647(0x7FFFFFFF), it indicates that the value is invalid."
 ::= { hwDcAirConditionEntry 10 }

hwDcAirRunTime OBJECT-TYPE
SYNTAX Integer32 (0..175200)
MAX-ACCESS read-only
STATUS current
DESCRIPTION
"Dc aircondition run time, Value range: 0 to 175200.Unit: H,the value is an integer (.0). If the value is 2147483647(0x7FFFFFFF), it indicates that the value is invalid."
 ::= { hwDcAirConditionEntry 11 }

hwDcAirDCInputVoltage OBJECT-TYPE
SYNTAX Integer32 (0..720)
MAX-ACCESS read-only
STATUS current
DESCRIPTION
"Dc aircondition input voltage, Value range: 0.0 to 720.0.Unit: V.and the value is accurate to one decimal space (.1). If the value is 2147483647(0x7FFFFFFF), it indicates that the value is invalid."
 ::= { hwDcAirConditionEntry 12 }

hwDcAirEnterChannelTemp OBJECT-TYPE
SYNTAX Integer32 ( -500..1000)
MAX-ACCESS read-only
STATUS current
DESCRIPTION
"Dc aircondition enter channel temperature, Value range:-500.0 to 1000.0.Unit: degC.and the value is accurate to one decimal space (.1). If the value is 2147483647(0x7FFFFFFF), it indicates that the value is invalid."
 ::= { hwDcAirConditionEntry 13 }

hwDcAirPowerOnTempPoint OBJECT-TYPE
SYNTAX Integer32 ( -200..800)
MAX-ACCESS read-write
STATUS current
DESCRIPTION
"Dc aircondition power on temperature point, Value range:-200.0 to 800.0.Unit: degC.and the value is accurate to one decimal space (.1). If the value is 2147483647(0x7FFFFFFF), it indicates that the value is invalid."
 ::= { hwDcAirConditionEntry 14 }

hwDcAirPowerOffTempPoint OBJECT-TYPE
SYNTAX Integer32 ( -200..800)
MAX-ACCESS read-write
STATUS current
DESCRIPTION
"Dc aircondition power off temperature point, Value range:-20 to 80 Unit: degC.and the value is accurate to one decimal space (.1). If the value is 2147483647(0x7FFFFFFF), it indicates that the value is invalid."
 ::= { hwDcAirConditionEntry 15 }

hwDcAirPowerOnBatteryTempPoint OBJECT-TYPE
SYNTAX Integer32 ( -200..800)
MAX-ACCESS read-write
STATUS current
DESCRIPTION
"Dc aircondition power on battery temperature point, Value range:-200.0 to 800.0.Unit: V.and the value is accurate to one decimal space (.1). If the value is 2147483647(0x7FFFFFFF), it indicates that the value is invalid."
 ::= { hwDcAirConditionEntry 16 }

hwAcOffEnergySaving OBJECT-TYPE
SYNTAX INTEGER
{
disable(1),
enable(2)
}
MAX-ACCESS read-write
STATUS current
DESCRIPTION
"State of the Dc air energy saving status. It is an enumeration type: 
If the enumeration value is 1, it indicates that the Dc aircondition is in disable state;
If the enumeration value is 2, it indicates that the Dc aircondition is in enable state;"
 ::= { hwDcAirConditionEntry 17 }

hwDcAirPowerOnAcOffPoint OBJECT-TYPE
SYNTAX Integer32 ( -200..800)
MAX-ACCESS read-write
STATUS current
DESCRIPTION
"Dc aircondition power on ac fail temperature point, Value range:-200.0 to 800.0.Unit: degC.and the value is accurate to one decimal space (.1). If the value is 2147483647(0x7FFFFFFF), it indicates that the value is invalid."
 ::= { hwDcAirConditionEntry 18 }

hwDcAirPowerOffAcOffPoint OBJECT-TYPE
SYNTAX Integer32 ( -200..800)
MAX-ACCESS read-write
STATUS current
DESCRIPTION
"Dc aircondition power off ac fail temperature point, Value range:-200.0 to 800.0.Unit: degC.and the value is accurate to one decimal space (.1). If the value is 2147483647(0x7FFFFFFF), it indicates that the value is invalid."
 ::= { hwDcAirConditionEntry 19 }

hwDcAirCompressorStartTemp OBJECT-TYPE
SYNTAX Integer32 (200..500)
MAX-ACCESS read-write
STATUS current
DESCRIPTION
"Dc aircondition compressor start temperature point, Value range:200.0 to 500.0.Unit: degC.and the value is accurate to one decimal space (.1). If the value is 2147483647(0x7FFFFFFF), it indicates that the value is invalid."
 ::= { hwDcAirConditionEntry 20 }

hwDcAirOperStatus OBJECT-TYPE
SYNTAX INTEGER
{
standby(1),
run(2),
fault(3),
alarmResume(254),
other(255)
}
MAX-ACCESS read-only
STATUS current
DESCRIPTION
"State of the dc aircondition. It is an enumeration type: 
If the enumeration value is 1, it indicates that the Inverter is in the standby state;
If the enumeration value is 2, it indicates that the Inverter is in the run state;  
If the enumeration value is 3, it indicates that the Inverter is in the fault state;  
If the enumeration value is 254, it indicates that the Inverter is in the resume state;   
If the enumeration value is 255, it indicates Inverter operation status unknown. "
 ::= { hwDcAirConditionEntry 99 }

hwDcAirRowStatus OBJECT-TYPE
SYNTAX RowStatus
MAX-ACCESS read-create
STATUS current
DESCRIPTION
"RowStatus fo dc aircondition table."
 ::= { hwDcAirConditionEntry 100 }

hwSiteAcAmmeters OBJECT IDENTIFIER ::= { hwSiteMonitorMIBObjects 11 }

hwSiteAcAmmeterEquip OBJECT IDENTIFIER ::= { hwSiteAcAmmeters 2 }

hwSiteAcAmmeterTable OBJECT-TYPE
SYNTAX SEQUENCE OF HwSiteAcAmmeterEntry
MAX-ACCESS not-accessible
                                             STATUS current
                                             DESCRIPTION
"/"
 ::= { hwSiteAcAmmeterEquip 1 }

hwSiteAcAmmeterEntry OBJECT-TYPE
SYNTAX HwSiteAcAmmeterEntry
MAX-ACCESS not-accessible
                                             STATUS current
                                             DESCRIPTION
"/"
INDEX { hwAcAmmeterIndex }
 ::= { hwSiteAcAmmeterTable 1 }

HwSiteAcAmmeterEntry ::= SEQUENCE {
hwAcAmmeterIndex
 Unsigned32,
hwAcAmmeterEquipId
 Unsigned32,
hwAcAmmeterEquipName
 OCTET STRING,
hwAcAmmeterFrequency
 Unsigned32,
hwAcAmmeterPhaseL1Voltage
 Unsigned32,
hwAcAmmeterPhaseL2Voltage
 Unsigned32,
hwAcAmmeterPhaseL3Voltage
 Unsigned32,
hwAcAmmeterSetChannelNum
 Unsigned32,
hwAcAmmeterClear
 INTEGER,
hwAcAmmeterType
 Unsigned32,
hwAcAmmeterVersion
 OCTET STRING,
hwAcAmmeterPhaseL1CurrentCH1
 Unsigned32,
hwAcAmmeterPhaseL2CurrentCH1
 Unsigned32,
hwAcAmmeterPhaseL3CurrentCH1
 Unsigned32,
hwAcAmmeterTotalActivePowerCH1
 Integer32,
hwAcAmmeterTotalPowerFactorCH1
 Integer32,
hwAcAmmeterTotalActiveEngryAccCH1
 Unsigned32,
hwAcAmmeterPhaseL1CurrentCH2
 Unsigned32,
hwAcAmmeterPhaseL2CurrentCH2
 Unsigned32,
hwAcAmmeterPhaseL3CurrentCH2
 Unsigned32,
hwAcAmmeterTotalActivePowerCH2
 Integer32,
hwAcAmmeterTotalPowerFactorCH2
 Integer32,
hwAcAmmeterTotalActiveEngryAccCH2
 Unsigned32,
hwAcAmmeterPhaseL1CurrentCH3
 Unsigned32,
hwAcAmmeterPhaseL2CurrentCH3
 Unsigned32,
hwAcAmmeterPhaseL3CurrentCH3
 Unsigned32,
hwAcAmmeterTotalActivePowerCH3
 Integer32,
hwAcAmmeterTotalPowerFactorCH3
 Integer32,
hwAcAmmeterTotalActiveEngryAccCH3
 Unsigned32,
hwAcAmmeterOperStatus
 INTEGER,
hwAcAmmeterRowStatus
 RowStatus
}

hwAcAmmeterIndex OBJECT-TYPE
SYNTAX Unsigned32 (0..256)
MAX-ACCESS read-only
STATUS current
DESCRIPTION
"Ac Ammeter table index,which value range:1 to 256. Lines of the device list are restricted by the quantity of AcAmmeter"
 ::= { hwSiteAcAmmeterEntry 1 }

hwAcAmmeterEquipId OBJECT-TYPE
SYNTAX Unsigned32 (22001..22255)
MAX-ACCESS read-only
STATUS current
DESCRIPTION
"Ac Ammeter device ID. Value range: 022'001 to 022'255, in which the first digits indicate the device type and the last three digits indicate the device SN."
 ::= { hwSiteAcAmmeterEntry 2 }

hwAcAmmeterEquipName OBJECT-TYPE
SYNTAX OCTET STRING (SIZE (0..56))
MAX-ACCESS read-only
STATUS current
DESCRIPTION
"Ac Ammeter name, of the character string type, is used to specify Fans. Users can configure it.
Otherwise, the configured character can not be any other languages except English.
"
 ::= { hwSiteAcAmmeterEntry 3 }

hwAcAmmeterFrequency OBJECT-TYPE
SYNTAX Unsigned32 (0..1000)
MAX-ACCESS read-only
STATUS current
DESCRIPTION
"Ac Ammeter frequency, Value range: 0.00 to 1000.0.Unit: Hz.and the value is accurate to two decimal space (.2). If the value is 2147483647(0x7FFFFFFF), it indicates that the value is invalid."
 ::= { hwSiteAcAmmeterEntry 4 }

hwAcAmmeterPhaseL1Voltage OBJECT-TYPE
SYNTAX Unsigned32 (0..2000)
MAX-ACCESS read-only
STATUS current
DESCRIPTION
"Ac Ammeter phase a voltage, Value range: 0.00 to 2000.0.Unit: V.and the value is accurate to two decimal space (.2). If the value is 2147483647(0x7FFFFFFF), it indicates that the value is invalid."
 ::= { hwSiteAcAmmeterEntry 5 }

hwAcAmmeterPhaseL2Voltage OBJECT-TYPE
SYNTAX Unsigned32 (0..2000)
MAX-ACCESS read-only
STATUS current
DESCRIPTION
"Ac Ammeter phase b voltage, Value range: 0.00 to 2000.0.Unit: V.and the value is accurate to two decimal space (.2). If the value is 2147483647(0x7FFFFFFF), it indicates that the value is invalid."
 ::= { hwSiteAcAmmeterEntry 6 }

hwAcAmmeterPhaseL3Voltage OBJECT-TYPE
SYNTAX Unsigned32 (0..2000)
MAX-ACCESS read-only
STATUS current
DESCRIPTION
"Ac Ammeter phase c voltage, Value range: 0.00 to 2000.0.Unit: V.and the value is accurate to two decimal space (.2). If the value is 2147483647(0x7FFFFFFF), it indicates that the value is invalid."
 ::= { hwSiteAcAmmeterEntry 7 }

hwAcAmmeterSetChannelNum OBJECT-TYPE
SYNTAX Unsigned32 (0..4)
MAX-ACCESS read-write
STATUS current
DESCRIPTION
"Ac Ammeter set channel number, Value range: 0 to 4. Unit: rpm.and the value is accurate to two decimal space (.0). If the value is 2147483647(0x7FFFFFFF), it indicates that the value is invalid."
 ::= { hwSiteAcAmmeterEntry 8 }


SYNTAX INTEGER
{
clear(1),
}
MAX-ACCESS read-write
STATUS current
DESCRIPTION
"Ac Ammeter clear communication failure . It is an enumeration type: 
If the enumeration value is 1, it indicates that the ac ammeter clear communication failure alarm;"
 ::= { hwSiteAcAmmeterEntry 9 }

hwAcAmmeterType OBJECT-TYPE
SYNTAX Unsigned32 (0..65535)
MAX-ACCESS read-only
STATUS current
DESCRIPTION
"Ac Ammeter type, Value range: 0 to 65535. And the value is accurate to one decimal space (.0)."
 ::= { hwSiteAcAmmeterEntry 10 }

hwAcAmmeterVersion OBJECT-TYPE
SYNTAX OCTET STRING (SIZE (0..56))
MAX-ACCESS read-only
STATUS current
DESCRIPTION
"Ac Ammeter version, of the character string type, is used to specify Ac Ammeter. Users can not configure it."
 ::= { hwSiteAcAmmeterEntry 11 }

hwAcAmmeterPhaseL1CurrentCH1 OBJECT-TYPE
SYNTAX Unsigned32 (0..1000)
MAX-ACCESS read-only
STATUS current
DESCRIPTION
"Ac Ammeter phase a current of channel 1, Value range: 0.00 to 1000.0.Unit: A.and the value is accurate to two decimal space (.2). If the value is 2147483647(0x7FFFFFFF), it indicates that the value is invalid."
 ::= { hwSiteAcAmmeterEntry 12 }

hwAcAmmeterPhaseL2CurrentCH1 OBJECT-TYPE
SYNTAX Unsigned32 (0..1000)
MAX-ACCESS read-only
STATUS current
DESCRIPTION
"Ac Ammeter phase b current of channel 1, Value range: 0.00 to 1000.0.Unit: A.and the value is accurate to two decimal space (.2). If the value is 2147483647(0x7FFFFFFF), it indicates that the value is invalid."
 ::= { hwSiteAcAmmeterEntry 13 }

hwAcAmmeterPhaseL3CurrentCH1 OBJECT-TYPE
SYNTAX Unsigned32 (0..1000)
MAX-ACCESS read-only
STATUS current
DESCRIPTION
"Ac Ammeter phase c current of channel 1, Value range: 0.00 to If the value is 2147483647(0x7FFFFFFF), it indicates that the value is invalid.1000.0.Unit: A.and the value is accurate to two decimal space (.2)."
 ::= { hwSiteAcAmmeterEntry 14 }

hwAcAmmeterTotalActivePowerCH1 OBJECT-TYPE
SYNTAX Integer32 (-1000000..1000000)
MAX-ACCESS read-only
STATUS current
DESCRIPTION
"Ac Ammeter phase c current of channel 1, Value range: -1000000.00 to 1000000.00.Unit: kW.and the value is accurate to two decimal space (.2). If the value is 2147483647(0x7FFFFFFF), it indicates that the value is invalid."
 ::= { hwSiteAcAmmeterEntry 15 }

hwAcAmmeterTotalPowerFactorCH1 OBJECT-TYPE
SYNTAX Integer32 (-10..10)
MAX-ACCESS read-only
STATUS current
DESCRIPTION
"Ac Ammeter total power factor of channel 1, Value range: -10.00 to 10.00.and the value is accurate to two decimal space (.2). If the value is 2147483647(0x7FFFFFFF), it indicates that the value is invalid."
 ::= { hwSiteAcAmmeterEntry 16 }

hwAcAmmeterTotalActiveEngryAccCH1 OBJECT-TYPE
SYNTAX Unsigned32 (0..1000000000)
MAX-ACCESS read-only
STATUS current
DESCRIPTION
"Ac Ammeter total active engry acc of channel 1, Value range: 0.00 to 1000000000.00.Unit: A.and the value is accurate to two decimal space (.2). If the value is 2147483647(0x7FFFFFFF), it indicates that the value is invalid."
 ::= { hwSiteAcAmmeterEntry 17 }

hwAcAmmeterPhaseL1CurrentCH2 OBJECT-TYPE
SYNTAX Unsigned32 (0..1000)
MAX-ACCESS read-only
STATUS current
DESCRIPTION
"Ac Ammeter phase a current of channel 2, Value range: 0.00 to 1000.00.Unit: A.and the value is accurate to two decimal space (.2). If the value is 2147483647(0x7FFFFFFF), it indicates that the value is invalid."
 ::= { hwSiteAcAmmeterEntry 18 }

hwAcAmmeterPhaseL2CurrentCH2 OBJECT-TYPE
SYNTAX Unsigned32 (0..1000)
MAX-ACCESS read-only
STATUS current
DESCRIPTION
"Ac Ammeter phase b current of channel 2, Value range: 0.00 to 1000.00.Unit: A.and the value is accurate to two decimal space (.2). If the value is 2147483647(0x7FFFFFFF), it indicates that the value is invalid."
 ::= { hwSiteAcAmmeterEntry 19 }

hwAcAmmeterPhaseL3CurrentCH2 OBJECT-TYPE
SYNTAX Unsigned32 (0..1000)
MAX-ACCESS read-only
STATUS current
DESCRIPTION
"Ac Ammeter phase c current of channel 2, Value range: 0.00 to 1000.00.Unit: A.and the value is accurate to two decimal space (.2). If the value is 2147483647(0x7FFFFFFF), it indicates that the value is invalid."
 ::= { hwSiteAcAmmeterEntry 20 }

hwAcAmmeterTotalActivePowerCH2 OBJECT-TYPE
SYNTAX Integer32 (-1000000..1000000)
MAX-ACCESS read-only
STATUS current
DESCRIPTION
"Ac Ammeter phase c current of channel 2, Value range: -1000000.00 to 1000000.00.Unit: kW.and the value is accurate to two decimal space (.2). If the value is 2147483647(0x7FFFFFFF), it indicates that the value is invalid."
 ::= { hwSiteAcAmmeterEntry 21 }

hwAcAmmeterTotalPowerFactorCH2 OBJECT-TYPE
SYNTAX Integer32 (-10..10)
MAX-ACCESS read-only
STATUS current
DESCRIPTION
"Ac Ammeter total power factor of channel 2, Value range: -10.00 to 10.00.and the value is accurate to two decimal space (.2). If the value is 2147483647(0x7FFFFFFF), it indicates that the value is invalid."
 ::= { hwSiteAcAmmeterEntry 22 }

hwAcAmmeterTotalActiveEngryAccCH2 OBJECT-TYPE
SYNTAX Unsigned32 (0..1000000000)
MAX-ACCESS read-only
STATUS current
DESCRIPTION
"Ac Ammeter total active engry acc of channel 2, Value range: 0.00 to 1000000000.00.Unit: A.and the value is accurate to two decimal space (.2). If the value is 2147483647(0x7FFFFFFF), it indicates that the value is invalid."
 ::= { hwSiteAcAmmeterEntry 23 }

hwAcAmmeterPhaseL1CurrentCH3 OBJECT-TYPE
SYNTAX Unsigned32 (0..1000)
MAX-ACCESS read-only
STATUS current
DESCRIPTION
"Ac Ammeter phase a current of channel 3, Value range: 0.00 to 1000.00.Unit: A.and the value is accurate to two decimal space (.2). If the value is 2147483647(0x7FFFFFFF), it indicates that the value is invalid."
 ::= { hwSiteAcAmmeterEntry 24 }

hwAcAmmeterPhaseL2CurrentCH3 OBJECT-TYPE
SYNTAX Unsigned32 (0..1000)
MAX-ACCESS read-only
STATUS current
DESCRIPTION
"Ac Ammeter phase b current of channel 3, Value range: 0.00 to 1000.00.Unit: A.and the value is accurate to two decimal space (.2). If the value is 2147483647(0x7FFFFFFF), it indicates that the value is invalid."
 ::= { hwSiteAcAmmeterEntry 25 }

hwAcAmmeterPhaseL3CurrentCH3 OBJECT-TYPE
SYNTAX Unsigned32 (0..1000)
MAX-ACCESS read-only
STATUS current
DESCRIPTION
"Ac Ammeter phase c current of channel 3, Value range: 0.00 to 1000.00.Unit: A.and the value is accurate to two decimal space (.2). If the value is 2147483647(0x7FFFFFFF), it indicates that the value is invalid."
 ::= { hwSiteAcAmmeterEntry 26 }

hwAcAmmeterTotalActivePowerCH3 OBJECT-TYPE
SYNTAX Integer32 (-1000000..1000000)
MAX-ACCESS read-only
STATUS current
DESCRIPTION
"Ac Ammeter phase c current of channel 3, Value range: -1000000.00 to 1000000.00.Unit: kW.and the value is accurate to two decimal space (.2). If the value is 2147483647(0x7FFFFFFF), it indicates that the value is invalid."
 ::= { hwSiteAcAmmeterEntry 27 }

hwAcAmmeterTotalPowerFactorCH3 OBJECT-TYPE
SYNTAX Integer32 (-10..10)
MAX-ACCESS read-only
STATUS current
DESCRIPTION
"Ac Ammeter total power factor of channel 3, Value range: -10.00 to 10.00.and the value is accurate to two decimal space (.2). If the value is 2147483647(0x7FFFFFFF), it indicates that the value is invalid."
 ::= { hwSiteAcAmmeterEntry 28 }

hwAcAmmeterTotalActiveEngryAccCH3 OBJECT-TYPE
SYNTAX Unsigned32 (0..1000000000)
MAX-ACCESS read-only
STATUS current
DESCRIPTION
"Ac Ammeter total active engry acc of channel 3, Value range: 0.00 to 1000000000.00.Unit: A.and the value is accurate to two decimal space (.2). If the value is 2147483647(0x7FFFFFFF), it indicates that the value is invalid."
 ::= { hwSiteAcAmmeterEntry 29 }

hwAcAmmeterOperStatus OBJECT-TYPE
SYNTAX INTEGER
{
normal (1),
fault (2),
other(255)
}
MAX-ACCESS read-only
STATUS current
DESCRIPTION
"State of the Ac Ammeter. It is an enumeration type: 
If the enumeration value is 1, it indicates that the Ac Ammeter is in the normal state;
If the enumeration value is 2, it indicates that the Ac Ammeter is in the fault state;  
If the enumeration value is 255, it indicates that the Ac Ammeter is in the other state;  "
 ::= { hwSiteAcAmmeterEntry 99 }

hwAcAmmeterRowStatus OBJECT-TYPE
SYNTAX RowStatus
MAX-ACCESS read-create
STATUS current
DESCRIPTION
"RowStatus fo dc Ac Ammeter table."
 ::= { hwSiteAcAmmeterEntry 100 }

hwSiteDG OBJECT IDENTIFIER ::= { hwSiteMonitorMIBObjects 12 }

hwDGGroup OBJECT IDENTIFIER ::= { hwSiteDG 1 }

hwDGGroupId OBJECT-TYPE
SYNTAX Unsigned32
MAX-ACCESS read-only
STATUS current
DESCRIPTION
"Device group ID of the DG module. It is the unique ID of the DG module group, and its default value: 023,000. 
The first digits indicate the device type and the last three digits indicate the device SN. If the last three digits are 000, it indicates a virtual device. "
 ::= { hwDGGroup 1 }

hwDGGroupName OBJECT-TYPE
SYNTAX OCTET STRING (SIZE (0..56))
MAX-ACCESS read-only
STATUS current
DESCRIPTION
"Name of the DG module group, character string type, is used to specify the DG module group. Otherwise, the configured character can not be any other languages except English."
 ::= { hwDGGroup 2 }

hwDGAmount OBJECT-TYPE
SYNTAX Unsigned32 (0..10)
MAX-ACCESS read-only
STATUS current
DESCRIPTION
"Total quantity of the DG modules. Value range: 0 to 10. Units:pcs."
 ::= { hwDGGroup 3 }

hwDG OBJECT IDENTIFIER ::= { hwSiteDG 2 }

hwDGTable OBJECT-TYPE
SYNTAX SEQUENCE OF HwDGEntry
MAX-ACCESS not-accessible
                                             STATUS current
                                             DESCRIPTION
"/"
 ::= { hwDG 1 }

hwDGEntry OBJECT-TYPE
SYNTAX HwDGEntry
MAX-ACCESS not-accessible
                                             STATUS current
                                             DESCRIPTION
"/"
INDEX { hwDGIndex }
 ::= { hwDGTable 1 }

HwDGEntry ::= SEQUENCE {
hwDGIndex
 Integer32,
hwDGEquipId
 Unsigned32,
hwDGEquipName
 OCTET STRING,
hwDGType
 INTEGER,
hwDGAphaseVoltage
 Unsigned32,
hwDGBphaseVoltage
 Unsigned32,
hwDGCphaseVoltage
 Unsigned32,
hwDGAphaseCurrent
 Unsigned32,
hwDGBphaseCurrent
 Unsigned32,
hwDGCphaseCurrent
 Unsigned32,
hwDGOutputPower
 Unsigned32,
hwDGFrequency
 Unsigned32,
hwDGBatteryVoltage
 Unsigned32,
hwDGTotalRuntime
 Unsigned32,
hwDGAphasePowerFactor
 Integer32,
hwDGBphasePowerFactor
 Integer32,
hwDGCphasePowerFactor
 Integer32,
hwDGLoadRate
 Unsigned32,
hwDGOnOffControl
 INTEGER,
hwDGFaultReset
 INTEGER,
hwDGMaintenanceConfirm
 INTEGER,
hwDGOperStatus
 INTEGER,
hwDGRowStatus
 RowStatus
}

hwDGIndex OBJECT-TYPE
SYNTAX Integer32 (0..256)
MAX-ACCESS read-only
STATUS current
DESCRIPTION
"DG table index,which value range:1 to 256. Lines of the device list are restricted by the quantity of DG."
 ::= { hwDGEntry 1 }

hwDGEquipId OBJECT-TYPE
SYNTAX Unsigned32 (23001..23255)
MAX-ACCESS read-only
STATUS current
DESCRIPTION
"DG device ID. Value range: 023'001 to 023'255, in which the first digits indicate the device type and the last three digits indicate the device SN."
 ::= { hwDGEntry 2 }

hwDGEquipName OBJECT-TYPE
SYNTAX OCTET STRING (SIZE (0..56))
MAX-ACCESS read-only
STATUS current
DESCRIPTION
"Device name of the DG module, character string type, is used to specify the DG module. Otherwise, the configured character can not be any other languages except English."
 ::= { hwDGEntry 3 }

hwDGType OBJECT-TYPE
SYNTAX INTEGER
{
intelligent (1),
non_intelligent (2),
other(255)
}
MAX-ACCESS read-only
STATUS current
DESCRIPTION
"Specific type of the DG module. It is an enumeration type:
  If the enumeration value is 1, it indicates a intelligent DG module; 
  If the enumeration value is 2, it indicates a non_intelligent module; "
 ::= { hwDGEntry 4 }

hwDGAphaseVoltage OBJECT-TYPE
SYNTAX Unsigned32 (0..5000)
MAX-ACCESS read-only
STATUS current
DESCRIPTION
"A-phase voltage. Value range: 0 to 500, units: V, and the value is accurate to one decimal place (.1)."
 ::= { hwDGEntry 5 }

hwDGBphaseVoltage OBJECT-TYPE
SYNTAX Unsigned32 (0..5000)
MAX-ACCESS read-only
STATUS current
DESCRIPTION
"B-phase voltage. Value range: 0 to 500, units: V, and the value is accurate to one decimal place (.1)."
 ::= { hwDGEntry 6 }

hwDGCphaseVoltage OBJECT-TYPE
SYNTAX Unsigned32 (0..5000)
MAX-ACCESS read-only
STATUS current
DESCRIPTION
"C-phase voltage. Value range: 0 to 500, units: V, and the value is accurate to one decimal place (.1)."
 ::= { hwDGEntry 7 }

hwDGAphaseCurrent OBJECT-TYPE
SYNTAX Unsigned32 (0..100)
MAX-ACCESS read-only
STATUS current
DESCRIPTION
"A-phase current. Value range: 0 to 100, units: A, and the value is  an integer (.0)."
 ::= { hwDGEntry 8 }

hwDGBphaseCurrent OBJECT-TYPE
SYNTAX Unsigned32 (0..100)
MAX-ACCESS read-only
STATUS current
DESCRIPTION
"B-phase current. Value range: 0 to 100, units: A, and the value is  an integer (.0)."
 ::= { hwDGEntry 9 }

hwDGCphaseCurrent OBJECT-TYPE
SYNTAX Unsigned32 (0..100)
MAX-ACCESS read-only
STATUS current
DESCRIPTION
"C-phase current. Value range: 0 to 100, units: A, and the value is  an integer (.0)."
 ::= { hwDGEntry 10 }

hwDGOutputPower OBJECT-TYPE
SYNTAX Unsigned32 (0..1000)
MAX-ACCESS read-only
STATUS current
DESCRIPTION
"DG output power.Value range: 0 to 100, units: kw, and the value is one decimal space (.1)."
 ::= { hwDGEntry 11 }

hwDGFrequency OBJECT-TYPE
SYNTAX Unsigned32 (50..1200)
MAX-ACCESS read-only
STATUS current
DESCRIPTION
"The frequency of DG. Value range: 5 to 120, units: Hz, and the value is one decimal space (.1)."
 ::= { hwDGEntry 12 }

hwDGBatteryVoltage OBJECT-TYPE
SYNTAX Unsigned32 (0..240)
MAX-ACCESS read-only
STATUS current
DESCRIPTION
"The voltage of DG battery. Value range: 0 to 24, units: V, and the value is one decimal space (.1)."
 ::= { hwDGEntry 13 }

hwDGTotalRuntime OBJECT-TYPE
SYNTAX Unsigned32 (0..8760000)
MAX-ACCESS read-only
STATUS current
DESCRIPTION
"The total running time of DG, Value range: 0 to 876000, units: h, and the value is one decimal space (.1)."
 ::= { hwDGEntry 14 }

hwDGAphasePowerFactor OBJECT-TYPE
SYNTAX Integer32 (-100..100)
MAX-ACCESS read-only
STATUS current
DESCRIPTION
"A phase power factor of DG, Value range: -1 to 1, units: , and the value is two decimal space (.2)."
 ::= { hwDGEntry 15 }

hwDGBphasePowerFactor OBJECT-TYPE
SYNTAX Integer32 (-100..100)
MAX-ACCESS read-only
STATUS current
DESCRIPTION
"B phase power factor of DG, Value range: -1 to 1, units: , and the value is two decimal space (.2)."
 ::= { hwDGEntry 16 }

hwDGCphasePowerFactor OBJECT-TYPE
SYNTAX Integer32 (-100..100)
MAX-ACCESS read-only
STATUS current
DESCRIPTION
"C phase power factor of DG, Value range: -1 to 1, units: , and the value is two decimal space (.2)."
 ::= { hwDGEntry 17 }

hwDGLoadRate OBJECT-TYPE
SYNTAX Unsigned32 (0..1000)
MAX-ACCESS read-only
STATUS current
DESCRIPTION
"The load rate of DG, Value range: 0 to 100, units: %, and the value is one decimal space (.1). "
 ::= { hwDGEntry 18 }

hwDGOnOffControl OBJECT-TYPE
SYNTAX INTEGER
{
on (1),
off (2),
other(255)
}
MAX-ACCESS read-write
STATUS current
DESCRIPTION
"Power-on or power-off of the DG module, is an enumeration value. Users can modify the enumeration value of this node, thus controlling of the power-on or power-off of the DG module:
  If the NMS notifies the SNMP agent that this node is set to 1, it indicates power-on of the DG module;
  If the NMS notifies the SNMP agent that this node is set to 2, it indicates power-off of the DG module. "
 ::= { hwDGEntry 19 }

hwDGFaultReset OBJECT-TYPE
SYNTAX INTEGER
{
reset(1),
other(255)
}
MAX-ACCESS read-write
STATUS current
DESCRIPTION
"DG fault reset."
 ::= { hwDGEntry 20 }

hwDGMaintenanceConfirm OBJECT-TYPE
SYNTAX INTEGER
{
reset(1),
other(255)
}
MAX-ACCESS read-write
STATUS current
DESCRIPTION
"DG maintenance confirm."
 ::= { hwDGEntry 21 }

hwDGOperStatus OBJECT-TYPE
SYNTAX INTEGER
{
stop(1),
running(2),
other(255)
}
MAX-ACCESS read-only
STATUS current
DESCRIPTION
"State of the DG. It is an enumeration type: 
If the enumeration value is 1, it indicates that the DG is in the normal state;
If the enumeration value is 2, it indicates that the DG is in the fault state;  
If the enumeration value is 255, it indicates that the DG is in the other state;  "
 ::= { hwDGEntry 99 }

hwDGRowStatus OBJECT-TYPE
SYNTAX RowStatus
MAX-ACCESS read-create
STATUS current
DESCRIPTION
"RowStatus fo DG."
 ::= { hwDGEntry 100 }

hwSiteSSU OBJECT IDENTIFIER ::= { hwSiteMonitorMIBObjects 13 }

hwSSUGroup OBJECT IDENTIFIER ::= { hwSiteSSU 1 }

hwSSUGroupId OBJECT-TYPE
SYNTAX Unsigned32
MAX-ACCESS read-only
STATUS current
DESCRIPTION
"Device group ID of the SSU module. It is the unique ID of the SSU module group, and its default value: 024,000. 
The first digits indicate the device type and the last three digits indicate the device SN. If the last three digits are 000, it indicates a virtual device. "
 ::= { hwSSUGroup 1 }

hwSSUGroupName OBJECT-TYPE
SYNTAX OCTET STRING (SIZE (0..56))
MAX-ACCESS read-only
STATUS current
DESCRIPTION
"Name of the SSU module group, character string type, is used to specify the SSU module group. Otherwise, the configured character can not be any other languages except English."
 ::= { hwSSUGroup 2 }

hwSSUTotalCurrent OBJECT-TYPE
SYNTAX Unsigned32 (0..10000)
MAX-ACCESS read-only
STATUS current
DESCRIPTION
"The total output current of SSU. Value range: 0 to 1000, units: A, and the value is one decimal space (.1)."
 ::= { hwSSUGroup 3 }

hwSSUTotalOutputPower OBJECT-TYPE
SYNTAX Unsigned32 (0..100000000)
MAX-ACCESS read-only
STATUS current
DESCRIPTION
"The total output current of SSU. Value range: 0 to 10000000, units: kWh, and the value is one decimal space (.1)."
 ::= { hwSSUGroup 4 }

hwSSUClearLostAlarms OBJECT-TYPE
SYNTAX INTEGER
{
normal(1), 
clear(2),
other(255)
}
MAX-ACCESS read-write
STATUS current
DESCRIPTION
"Clear the lost alarm of SSU."
 ::= { hwSSUGroup 5 }

hwSSUAmount OBJECT-TYPE
SYNTAX Unsigned32 (0..100)
MAX-ACCESS read-only
STATUS current
DESCRIPTION
"Total quantity of the SSU modules. Value range: 0 to 100. Units:pcs."
 ::= { hwSSUGroup 6 }

hwSSU OBJECT IDENTIFIER ::= { hwSiteSSU 2 }

hwSSUTable OBJECT-TYPE
SYNTAX SEQUENCE OF HwSSUEntry
MAX-ACCESS not-accessible
                                             STATUS current
                                             DESCRIPTION
"/"
 ::= { hwSSU 1 }

hwSSUEntry OBJECT-TYPE
SYNTAX HwSSUEntry
MAX-ACCESS not-accessible
                                             STATUS current
                                             DESCRIPTION
"/"
INDEX { hwSSUIndex }
 ::= { hwSSUTable 1 }

HwSSUEntry ::= SEQUENCE {
hwSSUIndex
 Integer32,
hwSSUEquipId
 Unsigned32,
hwSSUEquipName
 OCTET STRING,
hwSSURunningState
 INTEGER,
hwSSUInputVoltage
 Unsigned32,
hwSSUOutputVoltage
 Unsigned32,
hwSSUOutputCurrent
 Unsigned32,
hwSSUAddress
 Unsigned32,
hwSSURowStatus
 RowStatus
}

hwSSUIndex OBJECT-TYPE
SYNTAX Integer32 (0..256)
MAX-ACCESS read-only
STATUS current
DESCRIPTION
"SSU table index,which value range:1 to 256. Lines of the device list are restricted by the quantity of SSU."
 ::= { hwSSUEntry 1 }

hwSSUEquipId OBJECT-TYPE
SYNTAX Unsigned32 (24001..24255)
MAX-ACCESS read-only
STATUS current
DESCRIPTION
"SSU device ID. Value range: 024'001 to 024'255, in which the first digits indicate the device type and the last three digits indicate the device SN."
 ::= { hwSSUEntry 2 }

hwSSUEquipName OBJECT-TYPE
SYNTAX OCTET STRING (SIZE (0..56))
MAX-ACCESS read-only
STATUS current
DESCRIPTION
"Device name of the SSU module, character string type, is used to specify the SSU module. Otherwise, the configured character can not be any other languages except English."
 ::= { hwSSUEntry 3 }

hwSSURunningState OBJECT-TYPE
SYNTAX INTEGER
{
on(1),
off(2),
nullOper(255)
}
MAX-ACCESS read-only
STATUS current
DESCRIPTION
"The running status of the SSU module. It is an enumeration type: 
  If the enumeration value is 1, it indicates that the SSU module is power on ;
  If the enumeration value is 2, it indicates that the SSU module is power off; "
 ::= { hwSSUEntry 4 }

hwSSUInputVoltage OBJECT-TYPE
SYNTAX Unsigned32 (0..2000)
MAX-ACCESS read-only
STATUS current
DESCRIPTION
"The input voltage of SSU, Value range: 0 to 200, units: V, and the value is one decimal space (.1)."
 ::= { hwSSUEntry 5 }

hwSSUOutputVoltage OBJECT-TYPE
SYNTAX Unsigned32 (0..2000)
MAX-ACCESS read-only
STATUS current
DESCRIPTION
"The output voltage of SSU, Value range: 0 to 200, units: V, and the value is one decimal space (.1)."
 ::= { hwSSUEntry 6 }

hwSSUOutputCurrent OBJECT-TYPE
SYNTAX Unsigned32 (0..10000)
MAX-ACCESS read-only
STATUS current
DESCRIPTION
"The output current of SSU, Value range: 0 to 1000, units: A, and the value is one decimal space (.1)."
 ::= { hwSSUEntry 7 }

hwSSUAddress OBJECT-TYPE
SYNTAX Unsigned32 (0..100   )
MAX-ACCESS read-only
STATUS current
DESCRIPTION
"The address of SSU, Value range: 0 to 100, units: , and the value is  an integer (.0)."
 ::= { hwSSUEntry 8 }

hwSSURowStatus OBJECT-TYPE
SYNTAX RowStatus (0..256)
MAX-ACCESS read-create
STATUS current
DESCRIPTION
"RowStatus fo SSU."
 ::= { hwSSUEntry 100 }

hwSiteBatteryCabinets OBJECT IDENTIFIER ::= { hwSiteMonitorMIBObjects 14 }

hwSiteBatteryCabinetEquip OBJECT IDENTIFIER ::= { hwSiteBatteryCabinets 2 }

hwSiteBatteryCabinetTable OBJECT-TYPE
SYNTAX SEQUENCE OF HwSiteBatteryCabinetEntry
MAX-ACCESS not-accessible
                                             STATUS current
                                             DESCRIPTION
"/"
 ::= { hwSiteBatteryCabinetEquip 1 }

hwSiteBatteryCabinetEntry OBJECT-TYPE
SYNTAX HwSiteBatteryCabinetEntry
MAX-ACCESS not-accessible
                                             STATUS current
                                             DESCRIPTION
"/"
INDEX { hwBatteryCabinetIndex }
 ::= { hwSiteBatteryCabinetTable 1 }

HwSiteBatteryCabinetEntry ::= SEQUENCE {
hwBatteryCabinetIndex
 Unsigned32,
hwBatteryCabinetEquipId
 Unsigned32,
hwBatteryCabinetEquipName
 OCTET STRING,
hwBatteryCabinetIndoorVentTemp
 Integer32,
hwBatteryCabinetBattTemp
 Integer32,
hwBatteryCabinetFan1Speed
 Integer32,
hwBatteryCabinetFan2Speed
 Integer32,
hwBatteryCabinetFan3Speed
 Integer32,
hwBatteryCabinetFan4Speed
 Integer32,
hwBatteryCabinetAirConditionerStatus
 INTEGER,
hwBatteryCabinetCompressorStatus
 INTEGER,
hwBatteryCabinetInternalFanSpeed
 Integer32,
hwBatteryCabinetExternalFanSpeed
 Integer32,
hwBatteryCabinetAirConditionerRuntime
 Unsigned32,
hwBatteryCabinetCompressorRuntime
 Unsigned32,
hwBatteryCabinetAirConWorkTemp
 Integer32,
hwBatteryCabinetAirConStopTemp
 Integer32,
hwBatteryCabinetOperStatus
 INTEGER,
hwBatteryCabinetRowStatus
 RowStatus
}

hwBatteryCabinetIndex OBJECT-TYPE
SYNTAX Unsigned32 (0..256)
MAX-ACCESS read-only
STATUS current
DESCRIPTION
"Battery Cabinet table index,which value is according to the actual subject. Lines of the device list are restricted by the quantity of Battery Cabinet"
 ::= { hwSiteBatteryCabinetEntry 1 }

hwBatteryCabinetEquipId OBJECT-TYPE
SYNTAX Unsigned32 (25001..25255)
MAX-ACCESS read-only
STATUS current
DESCRIPTION
"Battery Cabinet device ID. Value range: 025'001 to 025'255, in which the first digits indicate the device type and the last three digits indicate the device SN."
 ::= { hwSiteBatteryCabinetEntry 2 }

hwBatteryCabinetEquipName OBJECT-TYPE
SYNTAX OCTET STRING (SIZE (0..56))
MAX-ACCESS read-only
STATUS current
DESCRIPTION
"Battery Cabinet name, of the character string type, is used to specify battery cabinet. Users can configure it.
Otherwise, the configured character can not be any other languages except English.
"
 ::= { hwSiteBatteryCabinetEntry 3 }

hwBatteryCabinetIndoorVentTemp OBJECT-TYPE
SYNTAX Integer32 ( -40..100)
MAX-ACCESS read-only
STATUS current
DESCRIPTION
"Indoor vent temperature. It is an environment parameter collected in real time. Value range: -40 to +100, units: centigrade, and the value is an integer (.0).  If the value is -99999, it indicates that the temperature sensor is not configured."
 ::= { hwSiteBatteryCabinetEntry 4 }

hwBatteryCabinetBattTemp OBJECT-TYPE
SYNTAX Integer32 ( -40..100)
MAX-ACCESS read-only
STATUS current
DESCRIPTION
"Battery temperature. It is an environment parameter collected in real time. Value range: -40 to +100, units: centigrade, and the value is an integer (.0).  If the value is -99999, it indicates that the temperature sensor is not configured."
 ::= { hwSiteBatteryCabinetEntry 5 }

hwBatteryCabinetFan1Speed OBJECT-TYPE
SYNTAX Integer32 (0..10000)
MAX-ACCESS read-only
STATUS current
DESCRIPTION
"Fan 1 speed, Value range: 0.0 to 10000.0.Unit: rpm,the value is an integer (.0). If the value is -1, it indicates that the fan is not configured."
 ::= { hwSiteBatteryCabinetEntry 6 }

hwBatteryCabinetFan2Speed OBJECT-TYPE
SYNTAX Integer32 (0..10000)
MAX-ACCESS read-only
STATUS current
DESCRIPTION
"Fan 2 speed, Value range: 0.0 to 10000.0.Unit: rpm,the value is an integer (.0). If the value is -1, it indicates that the fan is not configured."
 ::= { hwSiteBatteryCabinetEntry 7 }

hwBatteryCabinetFan3Speed OBJECT-TYPE
SYNTAX Integer32 (0..10000)
MAX-ACCESS read-only
STATUS current
DESCRIPTION
"Fan 3 speed, Value range: 0.0 to 10000.0.Unit: rpm,the value is an integer (.0). If the value is -1, it indicates that the fan is not configured."
 ::= { hwSiteBatteryCabinetEntry 8 }

hwBatteryCabinetFan4Speed OBJECT-TYPE
SYNTAX Integer32 (0..10000)
MAX-ACCESS read-only
STATUS current
DESCRIPTION
"Fan 4 speed, Value range: 0.0 to 10000.0.Unit: rpm,the value is an integer (.0). If the value is -1, it indicates that the fan is not configured."
 ::= { hwSiteBatteryCabinetEntry 9 }

hwBatteryCabinetAirConditionerStatus OBJECT-TYPE
SYNTAX INTEGER
{
standby(1),
run(2),
fault(3),
other(255)
}
MAX-ACCESS read-only
STATUS current
DESCRIPTION
"State of the airconditioner. It is an enumeration type: 
If the enumeration value is 1, it indicates that the airconditioner is in the standby state;
If the enumeration value is 2, it indicates that the airconditioner is in the run state;  
If the enumeration value is 3, it indicates that the airconditioner is in the fault state;  
If the enumeration value is 255, it indicates airconditioner status unknown. "
 ::= { hwSiteBatteryCabinetEntry 10 }

hwBatteryCabinetCompressorStatus OBJECT-TYPE
SYNTAX INTEGER
{
standby(1),
run(2),
fault(3),
other(255)
}
MAX-ACCESS read-only
STATUS current
DESCRIPTION
"State of the compressor. It is an enumeration type: 
If the enumeration value is 1, it indicates that the compressor is in the standby state;
If the enumeration value is 2, it indicates that the compressor is in the run state;  
If the enumeration value is 3, it indicates that the compressor is in the fault state;  
If the enumeration value is 255, it indicates compressor operation status unknown. "
 ::= { hwSiteBatteryCabinetEntry 11 }

hwBatteryCabinetInternalFanSpeed OBJECT-TYPE
SYNTAX Integer32 (0..10000)
MAX-ACCESS read-only
STATUS current
DESCRIPTION
"Internal Fan speed, Value range: 0.0 to 10000.0.Unit: rpm,the value is an integer (.0). If the value is -1, it indicates that the fan is not configured."
 ::= { hwSiteBatteryCabinetEntry 12 }

hwBatteryCabinetExternalFanSpeed OBJECT-TYPE
SYNTAX Integer32 (0..10000)
MAX-ACCESS read-only
STATUS current
DESCRIPTION
"External Fan speed, Value range: 0.0 to 10000.0.Unit: rpm,the value is an integer (.0). If the value is -1, it indicates that the temperature sensor is not configured."
 ::= { hwSiteBatteryCabinetEntry 13 }

hwBatteryCabinetAirConditionerRuntime OBJECT-TYPE
SYNTAX Unsigned32
MAX-ACCESS read-only
STATUS current
DESCRIPTION
"Total runtime of the air conditioner. Value units: minute (m), and the value is an integer (.0). If the value is 2147483647(0x7FFFFFFF), it indicates that the value is invalid."
 ::= { hwSiteBatteryCabinetEntry 14 }

hwBatteryCabinetCompressorRuntime OBJECT-TYPE
SYNTAX Unsigned32
MAX-ACCESS read-only
STATUS current
DESCRIPTION
"Total runtime of the compressor. Value units: minute (m), and the value is an integer (.0). If the value is 2147483647(0x7FFFFFFF), it indicates that the value is invalid."
 ::= { hwSiteBatteryCabinetEntry 15 }

hwBatteryCabinetAirConWorkTemp OBJECT-TYPE
SYNTAX Integer32 ( -20..80)
MAX-ACCESS read-write
STATUS current
DESCRIPTION
"Battery cabinet aircondition power on temperature point, Value range:-20 to 80 Unit: V.and the value is accurate to one decimal space (.1)."
 ::= { hwSiteBatteryCabinetEntry 16 }

hwBatteryCabinetAirConStopTemp OBJECT-TYPE
SYNTAX Integer32 ( -20..80)
MAX-ACCESS read-write
STATUS current
DESCRIPTION
"Battery cabinet aircondition power off temperature point, Value range:-20 to 80 Unit: V.and the value is accurate to one decimal space (.1)."
 ::= { hwSiteBatteryCabinetEntry 17 }

hwBatteryCabinetOperStatus OBJECT-TYPE
SYNTAX INTEGER
{
normal (1),
fault (2),
other(255)
}
MAX-ACCESS read-only
STATUS current
DESCRIPTION
"State of the Battery Cabinet. It is an enumeration type: 
If the enumeration value is 1, it indicates that the Inverter is in the normal state;
If the enumeration value is 2, it indicates that the Inverter is in the fault state;  
If the enumeration value is 255, it indicates that the Inverter is in the other state;  "
 ::= { hwSiteBatteryCabinetEntry 99 }

hwBatteryCabinetRowStatus OBJECT-TYPE
SYNTAX RowStatus
MAX-ACCESS read-create
STATUS current
DESCRIPTION
"RowStatus fo Battery Cabinet table."
 ::= { hwSiteBatteryCabinetEntry 100 }

hwSiteMonitorMIBTraps OBJECT IDENTIFIER ::= { hwSiteMonitorMIB 2 }

hwSiteAlarmTraps OBJECT IDENTIFIER ::= { hwSiteMonitorMIBTraps 1 }

hwSiteAlarmTrapsPrefix OBJECT IDENTIFIER ::= { hwSiteAlarmTraps 0 }

hwRectifierFaultAlarmTraps NOTIFICATION-TYPE
OBJECTS { hwAlarmTrapOrdinalNumber,hwAlarmText,hwAlarmLevel,hwAlarmSigDesc,hwSiteName,hwSiteAdminAddr,hwNetIdentifier,hwSiteDescription,hwRectEquipId,hwRectEquipName,hwRectOperStatus}
STATUS current
DESCRIPTION

"When rectifiers fault alarms happen, a alarm trap will be send. Its correlation binding parameters: Site ID, Site name, Site description, NE ID, Alarm name, Alarm single description, Alarm port description, Alarm severity, and Site alarm SN. Additionally, in order to identify the device, rectifier equipment ID and equipment name are also include in VB(variable bondings)."
 ::= { hwSiteAlarmTrapsPrefix 1 }

hwRectifierFaultAlarmResumeTraps NOTIFICATION-TYPE
OBJECTS { hwAlarmTrapOrdinalNumber,hwAlarmText,hwAlarmLevel,hwAlarmSigDesc,hwSiteName,hwSiteAdminAddr,hwNetIdentifier,hwSiteDescription,hwRectEquipId,hwRectEquipName,hwRectOperStatus}
STATUS current
DESCRIPTION

"Rectifier Fault alarm resolved.Its correlation binding parameters: Site ID, Site name, Site description, NE ID, Alarm name, Alarm single description, Alarm port description, Alarm severity, and Site alarm SN. Additionally, in order to identify the device, rectifier equipment ID and equipment name are also include in VB(variable bondings)."
 ::= { hwSiteAlarmTrapsPrefix 2 }

hwRectifierAbnormalAlarmTraps NOTIFICATION-TYPE
OBJECTS { hwAlarmTrapOrdinalNumber,hwAlarmText,hwAlarmLevel,hwAlarmSigDesc,hwSiteName,hwSiteAdminAddr,hwNetIdentifier,hwSiteDescription,hwRectEquipId,hwRectEquipName,hwRectOperStatus}
STATUS current
DESCRIPTION

"Rectifier abnormal alarm, because of communication failure, module protection, or turnoff. Its correlation binding parameters:  Site ID, Site name, Site description, NE ID, Alarm name, Alarm single description, Alarm port description, Alarm severity, and Site alarm SN. Additionally, in order to identify the device, rectifier equipment ID and equipment name are also include in VB(variable bondings)."
 ::= { hwSiteAlarmTrapsPrefix 3 }

hwRectifierAbnormalAlarmResumeTraps NOTIFICATION-TYPE
OBJECTS { hwAlarmTrapOrdinalNumber,hwAlarmText,hwAlarmLevel,hwAlarmSigDesc,hwSiteName,hwSiteAdminAddr,hwNetIdentifier,hwSiteDescription,hwRectEquipId,hwRectEquipName,hwRectOperStatus}
STATUS current
DESCRIPTION

"Rectifier abnormal alarm resume. Description.Its correlation binding parameters:  Site ID, Site name, Site description, NE ID, Alarm name, Alarm single description, Alarm port description, Alarm severity, and Site alarm SN. Additionally, in order to identify the device, rectifier equipment ID and equipment name are also include in VB(variable bondings)."
 ::= { hwSiteAlarmTrapsPrefix 4 }

hwBattLoopBreakAlarmTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Battery loop disconnect. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 5 }

hwBattLoopBreakAlarmResumeTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Battery loop break alarm resume. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 6 }

hwBattLvdAlarmTraps NOTIFICATION-TYPE
OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus}
STATUS current
DESCRIPTION

"Battery disconnect for low voltage. Its correlation binding parameters:  Site ID, Site name, Site description, NE ID, Alarm name, Alarm single description, Alarm port description, Alarm severity, and Site alarm SN. Additionally, in order to identify the device, battery LVD unit equipment ID and equipment name are also include in VB(variable bondings)."
 ::= { hwSiteAlarmTrapsPrefix 7 }

hwBattLvdAlarmResumeTraps NOTIFICATION-TYPE
OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus}
STATUS current
DESCRIPTION

"Battery LVD alarm resume. Its correlation binding parameters:  Site ID, Site name, Site description, NE ID, Alarm name, Alarm single description, Alarm port description, Alarm severity, and Site alarm SN. Additionally, in order to identify the device, battery LVD unit equipment ID and equipment name are also include in VB(variable bondings)."
 ::= { hwSiteAlarmTrapsPrefix 8 }

hwBattOverCurrAlarmTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Batterys charge in over current. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 9 }

hwBattOverCurrAlarmResumeTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Batterys over current alarm resume. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 10 }

hwBattStringTempAlarmTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Battery string temperature is too high or too low. Its correlation binding parameters:  Site ID, Site name, Site description, NE ID, Alarm name, Alarm single description, Alarm port description, Alarm severity, and Site alarm SN. Additionally, in order to identify the device, battery group ID and group name are also include in VB(variable bondings)."
 ::= { hwSiteAlarmTrapsPrefix 11 }

hwBattStringTempAlarmResumeTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Battery string temperature alarm resume. Its correlation binding parameters:  Site ID, Site name, Site description, NE ID, Alarm name, Alarm single description, Alarm port description, Alarm severity, and Site alarm SN. Additionally, in order to identify the device, battery group ID and group name are also include in VB(variable bondings)."
 ::= { hwSiteAlarmTrapsPrefix 12 }

hwBattDischargeAlarmTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Battery group discharge alarm. Its correlation binding parameters:  Site ID, Site name, Site description, NE ID, Alarm name, Alarm single description, Alarm port description, Alarm severity, and Site alarm SN. Additionally, in order to identify the device, battery group ID and group name are also include in VB(variable bondings)."
 ::= { hwSiteAlarmTrapsPrefix 13 }

hwBattDischargeAlarmResumeTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Battery group discharge alarm resume. Its correlation binding parameters:  Site ID, Site name, Site description, NE ID, Alarm name, Alarm single description, Alarm port description, Alarm severity, and Site alarm SN. Additionally, in order to identify the device, battery group ID and group name are also include in VB(variable bondings)."
 ::= { hwSiteAlarmTrapsPrefix 14 }

hwAcInputAlarmTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC absent or AC power off alarms happened. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 15 }

hwAcInputAlarmResumeTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC input alarm resumed. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 16 }

hwAcVoltAlarmTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC voltage too high or too low. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 17 }

hwAcVoltAlarmResumeTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC voltage alarm resume. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 18 }

hwDcVoltAlarmTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"DC voltage alarm. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 19 }

hwDcVoltAlarmResumeTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"DC voltage alarm resume. Its correlation binding parameters:  Site ID, Site name, Site description, NE ID, Alarm name, Alarm single description, Alarm port description, Alarm severity, and Site alarm SN. Additionally, in order to identify the device, DC equipment ID and equipment name are also include in VB(variable bondings)."
 ::= { hwSiteAlarmTrapsPrefix 20 }

hwLoadLvdAlarmTraps NOTIFICATION-TYPE
OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus}
STATUS current
DESCRIPTION

"Loads disconnect for low voltage. Its correlation binding parameters:  Site ID, Site name, Site description, NE ID, Alarm name, Alarm single description, Alarm port description, Alarm severity, and Site alarm SN. Additionally, in order to identify the device, load LVD unit equipment ID and equipment name are also include in VB(variable bondings)."
 ::= { hwSiteAlarmTrapsPrefix 21 }

hwLoadLvdAlarmResumeTraps NOTIFICATION-TYPE
OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus}
STATUS current
DESCRIPTION

"Load LVD alarm resume. Its correlation binding parameters:  Site ID, Site name, Site description, NE ID, Alarm name, Alarm single description, Alarm port description, Alarm severity, and Site alarm SN. Additionally, in order to identify the device, load LVD unit equipment ID and equipment name are also include in VB(variable bondings)."
 ::= { hwSiteAlarmTrapsPrefix 22 }

hwLoadFuseAlarmTraps NOTIFICATION-TYPE
OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus}
STATUS current
DESCRIPTION

"Load fuse broken down. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 23 }

hwLoadFuseAlarmResumeTraps NOTIFICATION-TYPE
OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus}
STATUS current
DESCRIPTION

"Load fuse alarm resume. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 24 }

hwEnvTempAlarmTraps NOTIFICATION-TYPE
OBJECTS { hwAlarmTrapOrdinalNumber,hwAlarmText,hwAlarmLevel,hwAlarmSigDesc,hwSiteName,hwSiteAdminAddr,hwNetIdentifier,hwSiteDescription,hwEnvTempEquipId,hwEnvTempEquipName,hwEnvTempSensorOperStatus}
STATUS current
DESCRIPTION

"Environment temperature is too high or too low. Its correlation binding parameters:  Site ID, Site name, Site description, NE ID, Alarm name, Alarm single description, Alarm port description, Alarm severity, and Site alarm SN. Additionally, in order to identify the device, envirenment temperature sensor equipment ID and equipment name are also include in VB(variable bondings)."
 ::= { hwSiteAlarmTrapsPrefix 25 }

hwEnvTempAlarmResumeTraps NOTIFICATION-TYPE
OBJECTS { hwAlarmTrapOrdinalNumber,hwAlarmText,hwAlarmLevel,hwAlarmSigDesc,hwSiteName,hwSiteAdminAddr,hwNetIdentifier,hwSiteDescription,hwEnvTempEquipId,hwEnvTempEquipName,hwEnvTempSensorOperStatus}
STATUS current
DESCRIPTION

"Environment temperature alarm resume. Its correlation binding parameters:  Site ID, Site name, Site description, NE ID, Alarm name, Alarm single description, Alarm port description, Alarm severity, and Site alarm SN. Additionally, in order to identify the device, envirenment temperature sensor equipment ID and equipment name are also include in VB(variable bondings)."
 ::= { hwSiteAlarmTrapsPrefix 26 }

hwEnvHumiAlarmTraps NOTIFICATION-TYPE
OBJECTS { hwAlarmTrapOrdinalNumber,hwAlarmText,hwAlarmLevel,hwAlarmSigDesc,hwSiteName,hwSiteAdminAddr,hwNetIdentifier,hwSiteDescription,hwEnvHumiEquipId,hwEnvHumiEquipName,hwEnvHumiSensorOperStatus}
STATUS current
DESCRIPTION

"Environment humidity is too high or too low. Its correlation binding parameters:  Site ID, Site name, Site description, NE ID, Alarm name, Alarm single description, Alarm port description, Alarm severity, and Site alarm SN. Additionally, in order to identify the device, envirenment humidity sensor equipment ID and equipment name are also include in VB(variable bondings)."
 ::= { hwSiteAlarmTrapsPrefix 27 }

hwEnvHumiAlarmResumeTraps NOTIFICATION-TYPE
OBJECTS { hwAlarmTrapOrdinalNumber,hwAlarmText,hwAlarmLevel,hwAlarmSigDesc,hwSiteName,hwSiteAdminAddr,hwNetIdentifier,hwSiteDescription,hwEnvHumiEquipId,hwEnvHumiEquipName,hwEnvHumiSensorOperStatus}
STATUS current
DESCRIPTION

"Environment humidity alarm resume. Its correlation binding parameters:  Site ID, Site name, Site description, NE ID, Alarm name, Alarm single description, Alarm port description, Alarm severity, and Site alarm SN. Additionally, in order to identify the device, envirenment humidity sensor equipment ID and equipment name are also include in VB(variable bondings)."
 ::= { hwSiteAlarmTrapsPrefix 28 }

hwSpareDigitalAlarmTraps NOTIFICATION-TYPE
OBJECTS { hwAlarmTrapOrdinalNumber,hwAlarmText,hwAlarmLevel,hwAlarmSigDesc,hwSiteName,hwSiteAdminAddr,hwNetIdentifier,hwSiteDescription,hwSpareDigitalEquipId,hwSpareDigitalEquipName,hwSpareDigitalOperStatus}
STATUS current
DESCRIPTION

"Spare digital fault. Its correlation binding parameters:  Site ID, Site name, Site description, NE ID, Alarm name, Alarm single description, Alarm port description, Alarm severity, and Site alarm SN. Additionally, in order to identify the device, Spare digital equipment ID and equipment name are also include in VB(variable bondings)."
 ::= { hwSiteAlarmTrapsPrefix 29 }

hwSpareDigitalAlarmResumeTraps NOTIFICATION-TYPE
OBJECTS { hwAlarmTrapOrdinalNumber,hwAlarmText,hwAlarmLevel,hwAlarmSigDesc,hwSiteName,hwSiteAdminAddr,hwNetIdentifier,hwSiteDescription,hwSpareDigitalEquipId,hwSpareDigitalEquipName,hwSpareDigitalOperStatus}
STATUS current
DESCRIPTION

"Spare digital alarm resume.Its correlation binding parameters:  Site ID, Site name, Site description, NE ID, Alarm name, Alarm single description, Alarm port description, Alarm severity, and Site alarm SN. Additionally, in order to identify the device, Spare digital equipment ID and equipment name are also include in VB(variable bondings)."
 ::= { hwSiteAlarmTrapsPrefix 30 }

hwDoorAlarmTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Door open. Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 31 }

hwDoorAlarmResumeTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Door alarm resume. Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 32 }

hwWaterAlarmTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Water alarm. Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 33 }

hwWaterAlarmResumeTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Water alarm resume. Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 34 }

hwSmokeAlarmTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Site is on fire, which is detected by smoke sensors. Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 35 }

hwSmokeAlarmResumeTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Smoke alarm resume. Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 36 }

hwWireAlarmTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Wire alarm.Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 37 }

hwWireAlarmResumeTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Wire alarm resume. Its correlation binding parameters:  Site ID, Site name, Site description, NE ID, Alarm name, Alarm single description, Alarm port description, Alarm severity, and Site alarm SN. Additionally, in order to identify the device, envirenment unit group ID and group name are also include in VB(variable bondings)."
 ::= { hwSiteAlarmTrapsPrefix 38 }

hwAcBreakerAlarmTraps NOTIFICATION-TYPE
OBJECTS { hwAlarmTrapOrdinalNumber,hwAlarmText,hwAlarmLevel,hwAlarmSigDesc,hwSiteName,hwSiteAdminAddr,hwNetIdentifier,hwSiteDescription,hwAcInputBreakerEquipId,hwAcInputBreakerEquipName,hwAcInputBreakerOperStatus}
STATUS current
DESCRIPTION

"AC breaker alarm.Its correlation binding parameters:  Site ID, Site name, Site description, NE ID, Alarm name, Alarm single description, Alarm port description, Alarm severity, and Site alarm SN. Additionally, in order to identify the device, AC distribution unit ID and its name are also include in VB(variable bondings)."
 ::= { hwSiteAlarmTrapsPrefix 39 }

hwAcBreakerAlarmResumeTraps NOTIFICATION-TYPE
OBJECTS { hwAlarmTrapOrdinalNumber,hwAlarmText,hwAlarmLevel,hwAlarmSigDesc,hwSiteName,hwSiteAdminAddr,hwNetIdentifier,hwSiteDescription,hwAcInputBreakerEquipId,hwAcInputBreakerEquipName,hwAcInputBreakerOperStatus}
STATUS current
DESCRIPTION

"AC breaker alarm resume.Its correlation binding parameters:  Site ID, Site name, Site description, NE ID, Alarm name, Alarm single description, Alarm port description, Alarm severity, and Site alarm SN. Additionally, in order to identify the device, AC distribution unit ID and its name are also include in VB(variable bondings)."
 ::= { hwSiteAlarmTrapsPrefix 40 }

hwMultiRectFailureAlarmTraps NOTIFICATION-TYPE
OBJECTS { hwAlarmTrapOrdinalNumber,hwAlarmText,hwAlarmLevel,hwAlarmSigDesc,hwSiteName,hwSiteAdminAddr,hwNetIdentifier,hwSiteDescription,hwRectsGroupId,hwRectsGroupName}
STATUS current
DESCRIPTION

"More than one rectifier reported fault alarms in the same time. Its correlation binding parameters:  Site ID, Site name, Site description, NE ID, Alarm name, Alarm single description, Alarm port description, Alarm severity, and Site alarm SN. Additionally, in order to identify the device, rectifier group ID and group name are also include in VB(variable bondings)."
 ::= { hwSiteAlarmTrapsPrefix 41 }

hwMultiRectFailureAlarmResumeTraps NOTIFICATION-TYPE
OBJECTS { hwAlarmTrapOrdinalNumber,hwAlarmText,hwAlarmLevel,hwAlarmSigDesc,hwSiteName,hwSiteAdminAddr,hwNetIdentifier,hwSiteDescription,hwRectsGroupId,hwRectsGroupName}
STATUS current
DESCRIPTION

"Multi-rectifiers fault alarm resume. Its correlation binding parameters:  Site ID, Site name, Site description, NE ID, Alarm name, Alarm single description, Alarm port description, Alarm severity, and Site alarm SN. Additionally, in order to identify the device, rectifier group ID and group name are also include in VB(variable bondings)."
 ::= { hwSiteAlarmTrapsPrefix 42 }

hwRectRedundAlarmTraps NOTIFICATION-TYPE
OBJECTS { hwAlarmTrapOrdinalNumber,hwAlarmText,hwAlarmLevel,hwAlarmSigDesc,hwSiteName,hwSiteAdminAddr,hwNetIdentifier,hwSiteDescription,hwRectsGroupId,hwRectsGroupName}
STATUS current
DESCRIPTION

"Rectifiers work redundantly, in this case that some of rectifiers will going to sleep. Its correlation binding parameters:  Site ID, Site name, Site description, NE ID, Alarm name, Alarm single description, Alarm port description, Alarm severity, and Site alarm SN. Additionally, in order to identify the device, rectifier group ID and group name are also include in VB(variable bondings)."
 ::= { hwSiteAlarmTrapsPrefix 43 }

hwRectRedundAlarmResumeTraps NOTIFICATION-TYPE
OBJECTS { hwAlarmTrapOrdinalNumber,hwAlarmText,hwAlarmLevel,hwAlarmSigDesc,hwSiteName,hwSiteAdminAddr,hwNetIdentifier,hwSiteDescription,hwRectsGroupId,hwRectsGroupName}
STATUS current
DESCRIPTION

"Rectifiers redundant alarm resume, when the power supply and requirement were in balance. Its correlation binding parameters:  Site ID, Site name, Site description, NE ID, Alarm name, Alarm single description, Alarm port description, Alarm severity, and Site alarm SN. Additionally, in order to identify the device, rectifier group ID and group name are also include in VB(variable bondings)."
 ::= { hwSiteAlarmTrapsPrefix 44 }

hwBattUnbalanceAlarmTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Battery works in unbalance state. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 45 }

hwBattUnbalanceAlarmResumeTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Battery unbalance alarm resume. Its correlation binding parameters:  Site ID, Site name, Site description, NE ID, Alarm name, Alarm single description, Alarm port description, Alarm severity, and Site alarm SN. Additionally, in order to identify the device, battery string equipment ID and equipment name are also include in VB(variable bondings)."
 ::= { hwSiteAlarmTrapsPrefix 46 }

hwAcFreqFaultAlarmTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC frequency is fault. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 47 }

hwAcFreqFaultAlarmResumeTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC frequency alarm resume. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 48 }

hwXmuSelfFaultAlarmTraps NOTIFICATION-TYPE
OBJECTS { hwAlarmTrapOrdinalNumber,hwAlarmText,hwAlarmLevel,hwAlarmSigDesc,hwSiteName,hwSiteAdminAddr,hwNetIdentifier,hwSiteDescription,hwMonEquipId,hwMonEquipName,hwMonitorOperStatus}
STATUS current
DESCRIPTION

"There are some fault in XMU itself. Its correlation binding parameters:  Site ID, Site name, Site description, NE ID, Alarm name, Alarm single description, Alarm port description, Alarm severity, and Site alarm SN. Additionally, in order to identify the device, monitor equipment ID and equipment name are also include in VB(variable bondings)."
 ::= { hwSiteAlarmTrapsPrefix 49 }

hwXmuSelfFaultAlarmResumeTraps NOTIFICATION-TYPE
OBJECTS { hwAlarmTrapOrdinalNumber,hwAlarmText,hwAlarmLevel,hwAlarmSigDesc,hwSiteName,hwSiteAdminAddr,hwNetIdentifier,hwSiteDescription,hwMonEquipId,hwMonEquipName,hwMonitorOperStatus}
STATUS current
DESCRIPTION

"XMU fault alarm resume. Its correlation binding parameters:  Site ID, Site name, Site description, NE ID, Alarm name, Alarm single description, Alarm port description, Alarm severity, and Site alarm SN. Additionally, in order to identify the device, monitor equipment ID and equipment name are also include in VB(variable bondings)."
 ::= { hwSiteAlarmTrapsPrefix 50 }

hwRs485CommAlarmTraps NOTIFICATION-TYPE
OBJECTS { hwAlarmTrapOrdinalNumber,hwAlarmText,hwAlarmLevel,hwAlarmSigDesc,hwSiteName,hwSiteAdminAddr,hwNetIdentifier,hwSiteDescription,hwMonEquipId,hwMonEquipName,hwMonitorOperStatus}
STATUS current
DESCRIPTION

"RS485 communication of monitors disconnect. Its correlation binding parameters:  Site ID, Site name, Site description, NE ID, Alarm name, Alarm single description, Alarm port description, Alarm severity, and Site alarm SN. Additionally, in order to identify the device, monitor equipment ID and equipment name are also include in VB(variable bondings)."
 ::= { hwSiteAlarmTrapsPrefix 51 }

hwRs485CommAlarmResumeTraps NOTIFICATION-TYPE
OBJECTS { hwAlarmTrapOrdinalNumber,hwAlarmText,hwAlarmLevel,hwAlarmSigDesc,hwSiteName,hwSiteAdminAddr,hwNetIdentifier,hwSiteDescription,hwMonEquipId,hwMonEquipName,hwMonitorOperStatus}
STATUS current
DESCRIPTION

"RS485 communication alarm resume. Its correlation binding parameters:  Site ID, Site name, Site description, NE ID, Alarm name, Alarm single description, Alarm port description, Alarm severity, and Site alarm SN. Additionally, in order to identify the device, monitor equipment ID and equipment name are also include in VB(variable bondings)."
 ::= { hwSiteAlarmTrapsPrefix 52 }

hwNetCommAlarmTraps NOTIFICATION-TYPE
OBJECTS { hwAlarmTrapOrdinalNumber,hwAlarmText,hwAlarmLevel,hwAlarmSigDesc,hwSiteName,hwSiteAdminAddr,hwNetIdentifier,hwSiteDescription,hwMonEquipId,hwMonEquipName,hwMonitorOperStatus}
STATUS current
DESCRIPTION

"Network communication of monitors disconnect. Its correlation binding parameters:  Site ID, Site name, Site description, NE ID, Alarm name, Alarm single description, Alarm port description, Alarm severity, and Site alarm SN. Additionally, in order to identify the device, monitor equipment ID and equipment name are also include in VB(variable bondings)."
 ::= { hwSiteAlarmTrapsPrefix 53 }

hwNetCommAlarmResumeTraps NOTIFICATION-TYPE
OBJECTS { hwAlarmTrapOrdinalNumber,hwAlarmText,hwAlarmLevel,hwAlarmSigDesc,hwSiteName,hwSiteAdminAddr,hwNetIdentifier,hwSiteDescription,hwMonEquipId,hwMonEquipName,hwMonitorOperStatus}
STATUS current
DESCRIPTION

"Network communication alarm resume. Its correlation binding parameters:  Site ID, Site name, Site description, NE ID, Alarm name, Alarm single description, Alarm port description, Alarm severity, and Site alarm SN. Additionally, in order to identify the device, monitor equipment ID and equipment name are also include in VB(variable bondings)."
 ::= { hwSiteAlarmTrapsPrefix 54 }

hwAcOffLongTimeAlarmTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC power off for a long time alarms happened. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 55 }

hwAcOffLongTimeAlarmResumeTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"AC power off for a long time alarms resume. Its correlation binding parameters:  Site ID, Site name, Site description, NE ID, Alarm name, Alarm single description, Alarm port description, Alarm severity, and Site alarm SN. Additionally, in order to identify the device, AC equipment ID and equipment name are also include in VB(variable bondings)."
 ::= { hwSiteAlarmTrapsPrefix 56 }

hwSpdAlarmTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Description."
 ::= { hwSiteAlarmTrapsPrefix 57 }

hwSpdAlarmResumeTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Description."
 ::= { hwSiteAlarmTrapsPrefix 58 }

hwBadBatteryTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 59 }

hwBadBatteryResumeTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 60 }

hwLvd2DisconnectingTraps NOTIFICATION-TYPE
OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus}
STATUS current
DESCRIPTION

"Description."
 ::= { hwSiteAlarmTrapsPrefix 61 }

hwLvd2DisconnectingResumeTraps NOTIFICATION-TYPE
OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus}
STATUS current
DESCRIPTION

"Description."
 ::= { hwSiteAlarmTrapsPrefix 62 }

hwBattHighTempTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Description."
 ::= { hwSiteAlarmTrapsPrefix 63 }

hwBattHighTempResumeTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Description."
 ::= { hwSiteAlarmTrapsPrefix 64 }

hwBattLowTempTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Description."
 ::= { hwSiteAlarmTrapsPrefix 65 }

hwBattLowTempResumeTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Description."
 ::= { hwSiteAlarmTrapsPrefix 66 }

hwDcUltraOverVoltageTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 67 }

hwDcUltraOverVoltageResumeTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 68 }

hwDcUltraUnderVoltageTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 69 }

hwDcUltraUnderVoltageResumeTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 70 }

hwUmiCommFailTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Description."
 ::= { hwSiteAlarmTrapsPrefix 71 }

hwUmiCommFailResumeTraps NOTIFICATION-TYPE
OBJECTS { hwAlarmTrapOrdinalNumber,hwAlarmText,hwAlarmLevel,hwAlarmSigDesc,hwSiteName,hwSiteAdminAddr,hwNetIdentifier,hwSiteDescription,hwEnvUnitsGroupId,hwEnvUnitsGroupName}
STATUS current
DESCRIPTION

"Description."
 ::= { hwSiteAlarmTrapsPrefix 72 }

hwShortTestFailTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 73 }

hwShortTestFailResumeTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 74 }

hwMissingBattTempSensorTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 75 }

hwMissingBattTempSensorResumeTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 76 }

hwBattTempSensorFaultTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 77 }

hwBattTempSensorFaultResumeTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 78 }

hwAcOverVoltageTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"Description."
 ::= { hwSiteAlarmTrapsPrefix 79 }

hwAcOverVoltageResumeTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"Description."
 ::= { hwSiteAlarmTrapsPrefix 80 }

hwAcUnderVoltageTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"Description."
 ::= { hwSiteAlarmTrapsPrefix 81 }

hwAcUnderVoltageResumeTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"Description."
 ::= { hwSiteAlarmTrapsPrefix 82 }

hwTcuFanAlarmTraps NOTIFICATION-TYPE
OBJECTS { hwAlarmTrapOrdinalNumber,hwAlarmText,hwAlarmLevel,hwAlarmSigDesc,hwSiteName,hwSiteAdminAddr,hwNetIdentifier,hwSiteDescription,hwFanEquipId,hwFanEquipName,hwFanOperStatus}
STATUS current
DESCRIPTION

"Description."
 ::= { hwSiteAlarmTrapsPrefix 83 }

hwTcuFanAlarmResumeTraps NOTIFICATION-TYPE
OBJECTS { hwAlarmTrapOrdinalNumber,hwAlarmText,hwAlarmLevel,hwAlarmSigDesc,hwSiteName,hwSiteAdminAddr,hwNetIdentifier,hwSiteDescription,hwFanEquipId,hwFanEquipName,hwFanOperStatus}
STATUS current
DESCRIPTION

"Description."
 ::= { hwSiteAlarmTrapsPrefix 84 }

hwTcuDcAirAlarmTraps NOTIFICATION-TYPE
OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus}
STATUS current
DESCRIPTION

"Description."
 ::= { hwSiteAlarmTrapsPrefix 85 }

hwTcuDcAirAlarmResumeTraps NOTIFICATION-TYPE
OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus}
STATUS current
DESCRIPTION

"Description."
 ::= { hwSiteAlarmTrapsPrefix 86 }

hwTripBreakAlarmTraps NOTIFICATION-TYPE
OBJECTS { hwAlarmTrapOrdinalNumber,hwAlarmText,hwAlarmLevel,hwAlarmSigDesc,hwSiteName,hwSiteAdminAddr,hwNetIdentifier,hwSiteDescription,hwAcInputBreakerEquipId,hwAcInputBreakerEquipName,hwAcInputBreakerOperStatus}
STATUS current
DESCRIPTION

"Description."
 ::= { hwSiteAlarmTrapsPrefix 87 }

hwTripBreakAlarmResumeTraps NOTIFICATION-TYPE
OBJECTS { hwAlarmTrapOrdinalNumber,hwAlarmText,hwAlarmLevel,hwAlarmSigDesc,hwSiteName,hwSiteAdminAddr,hwNetIdentifier,hwSiteDescription,hwAcInputBreakerEquipId,hwAcInputBreakerEquipName,hwAcInputBreakerOperStatus}
STATUS current
DESCRIPTION

"Description."
 ::= { hwSiteAlarmTrapsPrefix 88 }

hwTripBatteryCabinetAlarmTraps NOTIFICATION-TYPE
OBJECTS { hwAlarmTrapOrdinalNumber,hwAlarmText,hwAlarmLevel,hwAlarmSigDesc,hwSiteName,hwSiteAdminAddr,hwNetIdentifier,hwSiteDescription,hwBatteryCabinetEquipId,hwBatteryCabinetEquipName}
STATUS current
DESCRIPTION

"Description."
 ::= { hwSiteAlarmTrapsPrefix 89 }

hwTripBattCabAlarmResumeTraps NOTIFICATION-TYPE
OBJECTS { hwAlarmTrapOrdinalNumber,hwAlarmText,hwAlarmLevel,hwAlarmSigDesc,hwSiteName,hwSiteAdminAddr,hwNetIdentifier,hwSiteDescription,hwBatteryCabinetEquipId,hwBatteryCabinetEquipName}
STATUS current
DESCRIPTION

"Description."
 ::= { hwSiteAlarmTrapsPrefix 90 }

hwBattTestAlarmTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 103 }

hwBattTestAlarmResumeTraps NOTIFICATION-TYPE
OBJECTS { hwAlarmTrapOrdinalNumber,hwAlarmText,hwAlarmLevel,hwAlarmSigDesc,hwSiteName,hwSiteAdminAddr,hwNetIdentifier,hwSiteDescription,hwBattsGroupId,hwBattsGroupName}
STATUS current
DESCRIPTION

"Description."
 ::= { hwSiteAlarmTrapsPrefix 104 }

hwBattContactorFaultTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 105 }

hwBattContactorFaultResumeTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 106 }

hwBattFuseBreakAlarmTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Description."
 ::= { hwSiteAlarmTrapsPrefix 107 }

hwBattFuseBreakAlarmResumeTraps NOTIFICATION-TYPE
OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus}
STATUS current
DESCRIPTION

"Description."
 ::= { hwSiteAlarmTrapsPrefix 108 }

hwDCDAbnormalAlarmTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 109 }

hwDCDAbnormalAlarmResumeTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 110 }

hwACDAbnormalAlarmTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"Description."
 ::= { hwSiteAlarmTrapsPrefix 111 }

hwACDAbnormalAlarmResumeTraps NOTIFICATION-TYPE
OBJECTS { hwAlarmTrapOrdinalNumber,hwAlarmText,hwAlarmLevel,hwAlarmSigDesc,hwSiteName,hwSiteAdminAddr,hwNetIdentifier,hwSiteDescription,hwAcEquipId,hwAcEquipName,hwAcInputOperStatus}
STATUS current
DESCRIPTION

"Description."
 ::= { hwSiteAlarmTrapsPrefix 112 }

hwLoadOverCurrentAlarmTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 113 }

hwLoadOverCurrentAlarmResumeTraps NOTIFICATION-TYPE
OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus}
STATUS current
DESCRIPTION

"Description."
 ::= { hwSiteAlarmTrapsPrefix 114 }

hwEOSNoResponseAlarmTraps NOTIFICATION-TYPE
OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus}
STATUS current
DESCRIPTION

"Description."
 ::= { hwSiteAlarmTrapsPrefix 115 }

hwEOSNoResponseAlarmResumeTraps NOTIFICATION-TYPE
OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus}
STATUS current
DESCRIPTION

"Description."
 ::= { hwSiteAlarmTrapsPrefix 116 }

hwEOSOverLoadAlarmTraps NOTIFICATION-TYPE
OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus}
STATUS current
DESCRIPTION

"Description."
 ::= { hwSiteAlarmTrapsPrefix 117 }

hwEOSOverLoadAlarmResumeTraps NOTIFICATION-TYPE
OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus}
STATUS current
DESCRIPTION

"Description."
 ::= { hwSiteAlarmTrapsPrefix 118 }

hwInverterAlarmTraps NOTIFICATION-TYPE
OBJECTS { hwAlarmTrapOrdinalNumber,hwAlarmText,hwAlarmLevel,hwAlarmSigDesc,hwSiteName,hwSiteAdminAddr,hwNetIdentifier,hwSiteDescription,hwInverterEquipId,hwInverterEquipName,hwInverterOperStatus}
STATUS current
DESCRIPTION

"Description."
 ::= { hwSiteAlarmTrapsPrefix 119 }

hwInveterAlarmResumeTraps NOTIFICATION-TYPE
OBJECTS { hwAlarmTrapOrdinalNumber,hwAlarmText,hwAlarmLevel,hwAlarmSigDesc,hwSiteName,hwSiteAdminAddr,hwNetIdentifier,hwSiteDescription,hwInverterEquipId,hwInverterEquipName,hwInverterOperStatus}
STATUS current
DESCRIPTION

"Description."
 ::= { hwSiteAlarmTrapsPrefix 120 }

hwDGAlarmTraps NOTIFICATION-TYPE
OBJECTS { hwAlarmTrapOrdinalNumber,hwAlarmText,hwAlarmLevel,hwAlarmSigDesc,hwSiteName,hwSiteAdminAddr,hwNetIdentifier,hwSiteDescription}
STATUS current
DESCRIPTION

"Description."
 ::= { hwSiteAlarmTrapsPrefix 121 }

hwDGAlarmResumeTraps NOTIFICATION-TYPE
OBJECTS { hwAlarmTrapOrdinalNumber,hwAlarmText,hwAlarmLevel,hwAlarmSigDesc,hwSiteName,hwSiteAdminAddr,hwNetIdentifier,hwSiteDescription}
STATUS current
DESCRIPTION

"Description."
 ::= { hwSiteAlarmTrapsPrefix 122 }

hwSSUSummaryAlarmTraps NOTIFICATION-TYPE
OBJECTS { hwAlarmTrapOrdinalNumber,hwAlarmText,hwAlarmLevel,hwAlarmSigDesc,hwSiteName,hwSiteAdminAddr,hwNetIdentifier,hwSiteDescription}
STATUS current
DESCRIPTION

"Description."
 ::= { hwSiteAlarmTrapsPrefix 123 }

hwSSUSummaryAlarmResumeTraps NOTIFICATION-TYPE
OBJECTS { hwAlarmTrapOrdinalNumber,hwAlarmText,hwAlarmLevel,hwAlarmSigDesc,hwSiteName,hwSiteAdminAddr,hwNetIdentifier,hwSiteDescription}
STATUS current
DESCRIPTION

"Description."
 ::= { hwSiteAlarmTrapsPrefix 124 }

hwSSUAlarmTraps NOTIFICATION-TYPE
OBJECTS { hwAlarmTrapOrdinalNumber,hwAlarmText,hwAlarmLevel,hwAlarmSigDesc,hwSiteName,hwSiteAdminAddr,hwNetIdentifier,hwSiteDescription}
STATUS current
DESCRIPTION

"Description."
 ::= { hwSiteAlarmTrapsPrefix 125 }

hwSSUAlarmResumeTraps NOTIFICATION-TYPE
OBJECTS { hwAlarmTrapOrdinalNumber,hwAlarmText,hwAlarmLevel,hwAlarmSigDesc,hwSiteName,hwSiteAdminAddr,hwNetIdentifier,hwSiteDescription}
STATUS current
DESCRIPTION

"Description."
 ::= { hwSiteAlarmTrapsPrefix 126 }

hwSiteDevicesTraps OBJECT IDENTIFIER ::= { hwSiteMonitorMIBTraps 2 }

hwDevicesTrapsPrefix OBJECT IDENTIFIER ::= { hwSiteDevicesTraps 0 }

hwRectifiersInslotChange NOTIFICATION-TYPE
OBJECTS { hwDeviceTrapOrdinalNumber,hwSiteName,hwSiteAdminAddr,hwNetIdentifier,hwSiteDescription,hwRectEquipId,hwRectEquipName,hwRectOperStatus}
STATUS current
DESCRIPTION

"When the presence status of a rectifier changes, the node reports an event. Then the NMS adds or deletes the corresponding entry to or from hwRectConfigTable or hwRectOperTable. The bound information includes the site address, site name, site description, and NE identifier. In addition, the ID, name, and status of the rectifier are bound to identify the specific rectifier and its operation type. When an entry is added, the device status is reported as normal (1); when an entry is deleted, the device status is reported as commFail (4).
  This trap is the unique trigger condition that causes the NMS to add or delete entries to or from hwRectConfigTable or hwRectOperTable.
"
 ::= { hwDevicesTrapsPrefix 1 }

hwBatterysInslotChange NOTIFICATION-TYPE
OBJECTS { hwDeviceTrapOrdinalNumber,hwSiteName,hwSiteAdminAddr,hwNetIdentifier,hwSiteDescription,hwBattStringEquipId,hwBattStringEquipName,hwBattStringOperStatus}
STATUS current
DESCRIPTION

"When the presence status of a battery string changes, the node reports an event. Then the NMS adds or deletes the corresponding entry to or from hwBatttConfigTable or hwBatttOperTable. The bound information includes the site address, site name, site description, and NE identifier. In addition, the ID, name, and status of the battery string are bound to identify the specific battery string and its operation type. When an entry is added, the device status is reported as normal (1); when an entry is deleted, the device status is reported as loopBreak (4).
  This trap is the unique trigger condition that causes the NMS to add or delete entries to or from hwBatttConfigTable or hwBatttOperTable."
 ::= { hwDevicesTrapsPrefix 2 }

hwBattTestRecordsAdd NOTIFICATION-TYPE
OBJECTS { hwDeviceTrapOrdinalNumber,hwSiteName,hwSiteAdminAddr,hwNetIdentifier,hwSiteDescription}
STATUS current
DESCRIPTION

"After a new discharge test is conducted on a battery group, the node reports an event. The bound information includes the site address, site name, site description, and NE identifier. The NMS needs to add the corresponding entry to the battery test table. The test records are sorted by time in descending order. The battery test table holds a maximum of 10 test records. If the number of test records exceeds 10, the earlier records starting from the last but one record are deleted at a time because the last record is saved permanently.
  This trap is the unique trigger condition that causes the NMS to add entries from hwBattsTestResultTable.
  The battery test table allows you only to add entries."
 ::= { hwDevicesTrapsPrefix 3 }

hwEnvTempSensInslotChange NOTIFICATION-TYPE
OBJECTS { hwDeviceTrapOrdinalNumber,hwSiteName,hwSiteAdminAddr,hwNetIdentifier,hwSiteDescription,hwEnvTempEquipId,hwEnvTempEquipName,hwEnvTempSensorOperStatus}
STATUS current
DESCRIPTION

"When the presence status of an environment temperature sensor changes, the node reports an event. Then the NMS adds or deletes the corresponding entry to or from hwEvnTempSensorTable. The bound information includes the site address, site name, site description, and NE identifier. In addition, the ID, name, and status of the environment temperature sensor are bound to identify the specific environment temperature sensor and its operation type. When an entry is added, the device status is reported as normal (1); when an entry is deleted, the device status is reported as notInslot (4).
  This trap is the unique trigger condition that causes the NMS to add or delete entries to or from hwEnvTempSensorTable."
 ::= { hwDevicesTrapsPrefix 4 }

hwEnvHumiSensInslotChange NOTIFICATION-TYPE
OBJECTS { hwDeviceTrapOrdinalNumber,hwSiteName,hwSiteAdminAddr,hwNetIdentifier,hwSiteDescription,hwEnvHumiEquipId,hwEnvHumiEquipName,hwEnvHumiSensorOperStatus}
STATUS current
DESCRIPTION

"When the presence status of an environment humidity sensor changes, the trap reports an event. Then the NMS adds or deletes the corresponding entry to or from hwEvnHumiSensorTable. The bound information includes the site address, site name, site description, and NE identifier. In addition, the ID, name, and status of the environment humidity sensor are bound to identify the specific environment humidity sensor and its operation type. When an entry is added, the device status is reported as normal (1); when an entry is deleted, the device status is reported as notInslot (4).
  This trap is the unique trigger condition that causes the NMS to add or delete entries to or from hwEnvHumiSensorTable."
 ::= { hwDevicesTrapsPrefix 5 }

hwPDEsInslotChange NOTIFICATION-TYPE
OBJECTS { hwDeviceTrapOrdinalNumber,hwSiteName,hwSiteAdminAddr,hwNetIdentifier,hwSiteDescription}
STATUS current
DESCRIPTION

"Description."
 ::= { hwDevicesTrapsPrefix 6 }

hwInvertersInslotChange NOTIFICATION-TYPE
OBJECTS { hwDeviceTrapOrdinalNumber,hwSiteName,hwSiteAdminAddr,hwNetIdentifier,hwSiteDescription,hwInverterEquipId,hwInverterEquipName,hwInverterOperStatus}
STATUS current
DESCRIPTION

"Description."
 ::= { hwDevicesTrapsPrefix 7 }

END
